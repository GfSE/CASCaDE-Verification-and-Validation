## SSL-CONT-0106 (Requirement)
The Controller shall be able to sense and filter the
Aircraft Angle of Attack under normal conditions, unanticipated
atmospheric gust conditions and/or the failure or malfunctioning of
one or more sensors.

## SSL-CONT-0107 (Requirement)
The Controller shall be able to generate a control law
capable of reduce the gust effect by manipulating the Angle of
Attack ensuring structural integrity under all possible
circumstances.

## SSL-CONT-0131 (Requirement)
The controller
shall have a speed control loop
- DeriveReqt -> SSL-ELE-0103

## SSL-CONT-0132 (Requirement)
The controller
shall have a position control loop
- DeriveReqt -> SSL-ELE-0103
- DeriveReqt -> SSL-ELE-0103

## SSL-ELE-0021 (Requirement)
The elevator
should have a maximum planform area of x square
meters.

## SSL-ELE-0022 (Requirement)
The elevator
should have a weight of less than x kilograms.

## SSL-ELE-0023 (Requirement)
All the components or
parts mounted on the elevator shall be able to operate under
the power consumption restrictions resulting from dynamic,
unanticipated atmospheric turbulence conditions as specified in
ABD100.1.8,2.4.2 (or equivalent document).

## SSL-ELE-0024 (Requirement)
All the components or
parts mounted on the elevator shall operate according to
RTCA/DO-160G.

## SSL-ELE-0039 (Requirement)
The Elevator
shall be able to operate under loads up to x lb (or other
performance indicator) as specified in in FARxx (or corresponding
standard) while in dynamic, unanticipated atmospheric turbulence
conditions.

## SSL-ELE-0103 (Requirement)
The Elevator control
surfaces shall function ensuring the structural integrity of
the aircraft and avoiding critical stall effects resulting from
gust loads as specified in FAR 25.341 and 25.143 (or analogous EASA
CS 25) while in dynamic, unanticipated atmospheric turbulence
conditions.

## SSL-ELE-0200 (Design Constraint)
The Elevator chord to tail chord ratio (C_
E
/C_
h
) shall have a value
from 0.2 to 0.4

## SSL-ELE-0201 (Design Constraint)
The Elevator span to tail span ratio (b_
E
/b_
h
) shall have a value
from 0.8 to 1

## SSL-ELE-0202 (Design Constraint)
The Elevator maximum up elevator deflection (-
_Emax
) shall be -25
degrees

## SSL-ELE-0203 (Design Constraint)
The Elevator maximum down elevator deflection (+
_Emax
) shall be +20
degrees

## SSL-ELE-0204 (Design Constraint)
The Elevator planform area to horizontal tail planform area ratio
(S_
E
/S_
h
) shall have a value
from 0.15 to 0.4

## SSL-HA-0043 (Requirement)
The Hydraulic Actuator
of Elevator should have a length of less than x centimeters
on its longest dimension when fully assembled.

## SSL-HA-0044 (Requirement)
The Hydraulic Actuator
of Elevator should have a weight of less than x
kilograms.

## SSL-HA-0045 (Requirement)
The Hydraulic Actuator
of Elevator should have a volume of less than x cubic
centimeters.

## SSL-HA-0049 (Requirement)
The Hydraulic Actuator
of Elevator shall be able to operate in dynamic,
unanticipated atmospheric turbulence conditions as specified in
EUROCAE ED14 / RTCA/DO-160G Section 4.

## SSL-HA-0050 (Requirement)
The Hydraulic Actuator
of Elevator shall be able to operate in variable temperature
conditions as specified in RTCA/DO-160G Section 5.

## SSL-HA-0051 (Requirement)
The Hydraulic Actuator
of Elevator shall be able to operate in humid atmospheres
and anticipate adverse effects like corrosion or change of
characteristics derived from the absorption of humidity as
specified in RTCA/DO-160G Section 6.

## SSL-HA-0052 (Requirement)
The Hydraulic Actuator
of Elevator shall be able to operate within performance
standards after exposure to shocks experienced during normal
aircraft operations, like taxiing, landing or when the aircraft
encounters sudden gusts in a flight as specified in RTCA/DO-160G
Section 7.

## SSL-HA-0053 (Requirement)
The Hydraulic Actuator
of Elevator shall be able to operate under the operational
vibrations resulting from dynamic, unanticipated atmospheric
turbulence conditions as specified in RTCA/DO-160G Section
8.

## SSL-HA-0054 (Requirement)
The Hydraulic Actuator
of Elevator shall comply with the requirements and
procedures for aircraft equipment that may come into contact with
flammable fluids and vapors as specified in RTCA/DO-160G Section
9.

## SSL-HA-0055 (Requirement)
The Hydraulic Actuator
of Elevator shall be able to operate under the effects of
liquids water being sprayed or falling on them or the effects of
condensation as specified in RTCA/DO-160G Section 10.

## SSL-HA-0056 (Requirement)
The Hydraulic Actuator
of Elevator shall be able to withstand the deleterious
effects of fluid contaminants as specified in RTCA/DO-160G Section
11.

## SSL-HA-0057 (Requirement)
The Hydraulic Actuator
of Elevator shall be able to operate under the effects of
blowing sand and dust where carried by air movement at moderate
speeds as specified in RTCA/DO-160G Section 12.

## SSL-HA-0058 (Requirement)
The Hydraulic Actuator
of Elevator shall not be adversely affected by fungi under
conditions favorable for their development, namely, high humidity,
warm atmosphere and presence of inorganic salts, as specified in
RTCA/DO-160G Section 13.

## SSL-HA-0059 (Requirement)
The Hydraulic Actuator
of Elevator shall anticipate the effects of prolonged
exposure to a salt atmosphere or to salt fog experienced in normal
operations, like corrosion of metals, clogging or binding of moving
parts as a result of salt deposits, insulation fault or damage to
contacts and uncoated wiring, as specified in RTCA/DO-160G Section
14.

## SSL-HA-0060 (Requirement)
The Hydraulic Actuator
of Elevator shall operate to operate within performance
standards when exposed to icing conditions that would be
encountered under conditions of rapid changes in temperature,
altitude and humidity, as specified in RTCA/DO-160G Section
24.

## SSL-HA-0061 (Requirement)
The Hydraulic Actuator
of Elevator shall pass the tests conditions and procedure
for Flammability and Fire resistance as specified in RTCA/DO-160G
Section 26.

## SSL-HA-0062 (Requirement)
The Hydraulic Actuator
of Elevator shall be able to operate under the power
consumption restrictions resulting from dynamic, unanticipated
atmospheric turbulence conditions as specified in ABD100.1.8,2.4.2
(or equivalent document).

## SSL-HA-0077 (Requirement)
The Hydraulic Actuator
of Elevator shall have a stroke of at least x
millimeters.

## SSL-HA-0078 (Requirement)
The Hydraulic Actuator
of Elevator shall be able to provide a minimum torque of x
N∙m as specified in FARxx (or corresponding standard) while
in dynamic, unanticipated atmospheric turbulence conditions.

## SSL-HA-0079 (Requirement)
The Hydraulic Actuator
of Elevator shall be able to control the position of the
Aileron with a precision of x% (or other performance indicator) as
specified in FARxx (or corresponding standard) while in dynamic,
unanticipated atmospheric turbulence conditions.

## SSL-HA-0080 (Requirement)
The Hydraulic Actuator
of Elevator shall be able to control the speed of the
Aileron with a precision of x% (or other performance indicator) as
specified in FARxx (or corresponding standard) while in dynamic,
unanticipated atmospheric turbulence conditions.

## SSL-HA-0081 (Requirement)
The Hydraulic Actuator
of Elevator shall be able to operate up to x hours while in
dynamic, unanticipated atmospheric turbulence conditions.

## Notices in the file
Copyright © 2022 Boeing. All rights reserved
No license, LOTAR purposes
