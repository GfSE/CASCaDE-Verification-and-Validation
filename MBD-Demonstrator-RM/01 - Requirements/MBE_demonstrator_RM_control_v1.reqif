## AIL-LAF-0001 (Requirement)
The airplane
shall be able to detect structural and aerodynamic effects
resulting from gusts loads as specified in FARxx (or corresponding
standard) while in dynamic, unanticipated atmospheric turbulence
conditions.

## AIL-LAF-0002 (Requirement)
The airplane
shall be able to assess structural and aerodynamic effects
resulting from gusts loads as specified in FARxx (or corresponding
standard) while in dynamic, unanticipated atmospheric turbulence
conditions.

## AIL-LAF-0003 (Requirement)
The airplane
shall be able to eliminate structural and aerodynamic
effects resulting from gusts loads as specified in FARxx (or
corresponding standard) while in dynamic, unanticipated atmospheric
turbulence conditions.

## AIL-LAF-0004 (Requirement)
All the airborne
equipment of the airplane shall be able to operate under the
power consumption restrictions resulting from dynamic,
unanticipated atmospheric turbulence conditions as specified in
ABD100.1.8,2.4.2 (or equivalent document). This only applies to the
equipment that is necessary to operate the airplane under those
conditions.

## AIL-LAF-0005 (Requirement)
The airplane
shall be able to eliminate structural and aerodynamic
effects resulting from gusts loads as specified in FARxx (or
corresponding standard) with an efficiency of x% (or other
performance indicator) while in dynamic, unanticipated atmospheric
turbulence conditions.

## AIL-LAF-0006 (Requirement)
The airplane
shall guarantee a Maximum Flight Time (MFT) of x minutes
while in dynamic, unanticipated atmospheric turbulence
conditions.

## AIL-LAF-0007 (Requirement)
All the airborne
equipment of the airplane shall guarantee a Mean Time
Between Failures (MTBF) of x seconds while in dynamic,
unanticipated atmospheric turbulence conditions. This only applies
to the equipment that is necessary to operate the airplane under
those conditions.

## AIL-OTH-0008 (Requirement)
The airplane
should have a maximum wingspan of x meters.

## AIL-OTH-0009 (Requirement)
The airplane
should have a maximum overall length of x meters.

## AIL-OTH-0010 (Requirement)
The airplane
should have a maximum empty weight of x kilograms.

## AIL-OTH-0011 (Requirement)
All the airborne
equipment of the airplane shall be certified according to
RTCA/DO-160G.

## AIL-OTH-0013 (Requirement)
All the airborne
equipment of the airplane shall comply with the safety
requirements specified in FAR 25.1309.

## SYL-ECS-0014 (Requirement)
The Elevator Control
System shall be able to eliminate structural and aerodynamic
effects resulting from gusts loads as specified in FARxx (or
corresponding standard) while in dynamic, unanticipated atmospheric
turbulence conditions.
- DeriveReqt -> AIL-LAF-0003

## SYL-ECS-0015 (Requirement)
The Elevator Control
System shall be certified according to RTCA/DO-160G.
- DeriveReqt -> AIL-OTH-0011

## SYL-ECS-0017 (Requirement)
The Elevator Control
System shall be able to eliminate structural and aerodynamic
effects resulting from gusts loads as specified in FARxx (or
corresponding standard) with an efficiency of x% (or other
performance indicator) while in dynamic, unanticipated atmospheric
turbulence conditions.
- DeriveReqt -> AIL-LAF-0005

## SYL-ECS-0018 (Requirement)
The Elevator Control
System shall guarantee a Maximum Flight Time (MFT) of x
minutes while in dynamic, unanticipated atmospheric turbulence
conditions.
- DeriveReqt -> AIL-LAF-0006

## SYL-ECS-0019 (Requirement)
The Elevator Control
System shall guarantee a Mean Time Between Failures (MTBF)
of x seconds while in dynamic, unanticipated atmospheric turbulence
conditions.
- DeriveReqt -> AIL-LAF-0007

## SYL-ECS-0020 (Requirement)
The Elevator Control
System shall comply with the safety requirements specified
in FAR 25.1309.
- DeriveReqt -> AIL-OTH-0013

## SYL-ECS-0101 (Requirement)
The Elevator Control
System shall be able to assess impact on the aircraft
structure resulting from gusts loads as specified in FAR 25.341 and
25.143 (or analogous EASA CS 25) while in dynamic, unanticipated
atmospheric turbulence conditions.
- DeriveReqt -> AIL-LAF-0002

## SYL-ECS-0102 (Requirement)
The Elevator Control
System shall be able to detect gusts under all possible
circumstances not shown to be extremely improbable, including the
failure of one or several subsystems or components.
- DeriveReqt -> AIL-LAF-0001

## SSL-CONT-0106 (Requirement)
The Controller shall be able to sense and filter the
Aircraft Angle of Attack under normal conditions, unanticipated
atmospheric gust conditions and/or the failure or malfunctioning of
one or more sensors.

## SSL-CONT-0107 (Requirement)
The Controller shall be able to generate a control law
capable of reduce the gust effect by manipulating the Angle of
Attack ensuring structural integrity under all possible
circumstances.

## SSL-CONT-0131 (Requirement)
The controller
shall have a speed control loop
- DeriveReqt -> SSL-ELE-0103

## SSL-CONT-0132 (Requirement)
The controller
shall have a position control loop
- DeriveReqt -> SSL-ELE-0103
- DeriveReqt -> SSL-ELE-0103

## SSL-ELE-0021 (Requirement)
The elevator
should have a maximum planform area of x square
meters.
- DeriveReqt -> AIL-OTH-0009
- DeriveReqt -> AIL-OTH-0008

## SSL-ELE-0022 (Requirement)
The elevator
should have a weight of less than x kilograms.
- DeriveReqt -> AIL-OTH-0010

## SSL-ELE-0023 (Requirement)
All the components or
parts mounted on the elevator shall be able to operate under
the power consumption restrictions resulting from dynamic,
unanticipated atmospheric turbulence conditions as specified in
ABD100.1.8,2.4.2 (or equivalent document).
- DeriveReqt -> AIL-LAF-0004

## SSL-ELE-0024 (Requirement)
All the components or
parts mounted on the elevator shall operate according to
RTCA/DO-160G.
- DeriveReqt -> AIL-OTH-0011

## SSL-ELE-0039 (Requirement)
The Elevator
shall be able to operate under loads up to x lb (or other
performance indicator) as specified in in FARxx (or corresponding
standard) while in dynamic, unanticipated atmospheric turbulence
conditions.
- DeriveReqt -> SYL-ECS-0017

## SSL-ELE-0103 (Requirement)
The Elevator control
surfaces shall function ensuring the structural integrity of
the aircraft and avoiding critical stall effects resulting from
gust loads as specified in FAR 25.341 and 25.143 (or analogous EASA
CS 25) while in dynamic, unanticipated atmospheric turbulence
conditions.
- DeriveReqt -> SYL-ECS-0014

## SSL-ELE-0200 (Design Constraint)
The Elevator chord to tail chord ratio (C_
E
/C_
h
) shall have a value
from 0.2 to 0.4

## SSL-ELE-0201 (Design Constraint)
The Elevator span to tail span ratio (b_
E
/b_
h
) shall have a value
from 0.8 to 1

## SSL-ELE-0202 (Design Constraint)
The Elevator maximum up elevator deflection (-
_Emax
) shall be -25
degrees

## SSL-ELE-0203 (Design Constraint)
The Elevator maximum down elevator deflection (+
_Emax
) shall be +20
degrees

## SSL-ELE-0204 (Design Constraint)
The Elevator planform area to horizontal tail planform area ratio
(S_
E
/S_
h
) shall have a value
from 0.15 to 0.4

## SSL-HA-0043 (Requirement)
The Hydraulic Actuator
of Elevator should have a length of less than x centimeters
on its longest dimension when fully assembled.

## SSL-HA-0044 (Requirement)
The Hydraulic Actuator
of Elevator should have a weight of less than x
kilograms.
- DeriveReqt -> AIL-OTH-0010

## SSL-HA-0045 (Requirement)
The Hydraulic Actuator
of Elevator should have a volume of less than x cubic
centimeters.

## SSL-HA-0049 (Requirement)
The Hydraulic Actuator
of Elevator shall be able to operate in dynamic,
unanticipated atmospheric turbulence conditions as specified in
EUROCAE ED14 / RTCA/DO-160G Section 4.

## SSL-HA-0050 (Requirement)
The Hydraulic Actuator
of Elevator shall be able to operate in variable temperature
conditions as specified in RTCA/DO-160G Section 5.

## SSL-HA-0051 (Requirement)
The Hydraulic Actuator
of Elevator shall be able to operate in humid atmospheres
and anticipate adverse effects like corrosion or change of
characteristics derived from the absorption of humidity as
specified in RTCA/DO-160G Section 6.

## SSL-HA-0052 (Requirement)
The Hydraulic Actuator
of Elevator shall be able to operate within performance
standards after exposure to shocks experienced during normal
aircraft operations, like taxiing, landing or when the aircraft
encounters sudden gusts in a flight as specified in RTCA/DO-160G
Section 7.

## SSL-HA-0053 (Requirement)
The Hydraulic Actuator
of Elevator shall be able to operate under the operational
vibrations resulting from dynamic, unanticipated atmospheric
turbulence conditions as specified in RTCA/DO-160G Section
8.

## SSL-HA-0054 (Requirement)
The Hydraulic Actuator
of Elevator shall comply with the requirements and
procedures for aircraft equipment that may come into contact with
flammable fluids and vapors as specified in RTCA/DO-160G Section
9.

## SSL-HA-0055 (Requirement)
The Hydraulic Actuator
of Elevator shall be able to operate under the effects of
liquids water being sprayed or falling on them or the effects of
condensation as specified in RTCA/DO-160G Section 10.

## SSL-HA-0056 (Requirement)
The Hydraulic Actuator
of Elevator shall be able to withstand the deleterious
effects of fluid contaminants as specified in RTCA/DO-160G Section
11.

## SSL-HA-0057 (Requirement)
The Hydraulic Actuator
of Elevator shall be able to operate under the effects of
blowing sand and dust where carried by air movement at moderate
speeds as specified in RTCA/DO-160G Section 12.

## SSL-HA-0058 (Requirement)
The Hydraulic Actuator
of Elevator shall not be adversely affected by fungi under
conditions favorable for their development, namely, high humidity,
warm atmosphere and presence of inorganic salts, as specified in
RTCA/DO-160G Section 13.

## SSL-HA-0059 (Requirement)
The Hydraulic Actuator
of Elevator shall anticipate the effects of prolonged
exposure to a salt atmosphere or to salt fog experienced in normal
operations, like corrosion of metals, clogging or binding of moving
parts as a result of salt deposits, insulation fault or damage to
contacts and uncoated wiring, as specified in RTCA/DO-160G Section
14.

## SSL-HA-0060 (Requirement)
The Hydraulic Actuator
of Elevator shall operate to operate within performance
standards when exposed to icing conditions that would be
encountered under conditions of rapid changes in temperature,
altitude and humidity, as specified in RTCA/DO-160G Section
24.

## SSL-HA-0061 (Requirement)
The Hydraulic Actuator
of Elevator shall pass the tests conditions and procedure
for Flammability and Fire resistance as specified in RTCA/DO-160G
Section 26.

## SSL-HA-0062 (Requirement)
The Hydraulic Actuator
of Elevator shall be able to operate under the power
consumption restrictions resulting from dynamic, unanticipated
atmospheric turbulence conditions as specified in ABD100.1.8,2.4.2
(or equivalent document).

## SSL-HA-0077 (Requirement)
The Hydraulic Actuator
of Elevator shall have a stroke of at least x
millimeters.

## SSL-HA-0078 (Requirement)
The Hydraulic Actuator
of Elevator shall be able to provide a minimum torque of x
N∙m as specified in FARxx (or corresponding standard) while
in dynamic, unanticipated atmospheric turbulence conditions.

## SSL-HA-0079 (Requirement)
The Hydraulic Actuator
of Elevator shall be able to control the position of the
Aileron with a precision of x% (or other performance indicator) as
specified in FARxx (or corresponding standard) while in dynamic,
unanticipated atmospheric turbulence conditions.

## SSL-HA-0080 (Requirement)
The Hydraulic Actuator
of Elevator shall be able to control the speed of the
Aileron with a precision of x% (or other performance indicator) as
specified in FARxx (or corresponding standard) while in dynamic,
unanticipated atmospheric turbulence conditions.

## SSL-HA-0081 (Requirement)
The Hydraulic Actuator
of Elevator shall be able to operate up to x hours while in
dynamic, unanticipated atmospheric turbulence conditions.

## COL-CIC-0120 (Requirement)
The Control Interface
Component shall provide an input to the Controller of
U_gust=U_ref/2 (1-cos⁡(πs/H) )for 0≤s ≤2H
and U_gust=0 for 0 ≥2H . Where s is the distance penetrated
into the gust, H will be equal to 50 meters and U_ref will provided
in a different requirement.
- DeriveReqt -> SSL-CONT-0107

## COL-CIC-0121 (Requirement)
The Control Interface
Component shall contemplate a use case with with U_ref=10
m/s EAS, V_cruise=220 m/s TAS,height=h=10000 m in
which gust effects can be eliminated ensuring structural integrity
while in dynamic, unanticipated atmospheric turbulence
conditions.
- DeriveReqt -> SSL-CONT-0107

## COL-CIC-0126 (Requirement)
The Control Interface
Component should include a Liner Aircraft Longitudinal model
to assess the closed loop response of the AoA in small-angles use
cases.
- DeriveReqt -> SSL-CONT-0107

## COL-CIC-0127 (Requirement)
The Control Interface
Component should include an aerodynamic load model to assess
the closed loop response of the AoA in small-angles use
cases.
- DeriveReqt -> SSL-CONT-0107

## COL-CIC-0128 (Requirement)
The Control Interface
Component should take the AoA during curise as reference for
the sake of simplicity, so a_cruise = 0
- DeriveReqt -> SSL-CONT-0107

## COL-CIC-0129 (Requirement)
The controller
shall use a different redundant sensor signal when a
malfunctioning sensor is detected
- DeriveReqt -> SSL-CONT-0106

## COL-EDC-0073 (Requirement)
The Electric DC Motor of
the Hydraulic Actuator of Elevator shall have a volume of
less than x cubic centimeters.
- DeriveReqt -> SSL-HA-0045

## COL-EDC-0074 (Requirement)
The Electric DC Motor of
the Hydraulic Actuator of Elevator shall have a weight of
less than x grams.
- DeriveReqt -> SSL-HA-0044

## COL-EDC-0075 (Requirement)
The Electric DC Motor of
the Hydraulic Actuator of Elevator shall be supplied with a
minimum of x V.
- DeriveReqt -> SSL-HA-0051

## COL-EDC-0076 (Requirement)
The Electric DC Motor of
the Hydraulic Actuator of Elevator shall be supplied with a
maximum of x V.
- DeriveReqt -> SSL-HA-0051

## COL-EDC-0077 (Requirement)
The Electric DC Motor of
the Hydraulic Actuator of Elevator shall have a passive
rotor.
- DeriveReqt -> SSL-HA-0055

## COL-EDC-0078 (Requirement)
The Electric DC Motor of
the Hydraulic Actuator of Elevator shall have a slotted
stator.
- DeriveReqt -> SSL-HA-0055

## COL-EDC-0079 (Requirement)
The Electric DC Motor of
the Hydraulic Actuator of Elevator shall have a no load
speed of x R.P.M.
- DeriveReqt -> SSL-HA-0056

## COL-EDC-0088 (Requirement)
The Electric DC Motor of
the Hydraulic Actuator of Elevator shall be certified
according to RTCA/DO-160G Section X.
- DeriveReqt -> SSL-HA-0050
- DeriveReqt -> SSL-HA-0049

## COL-EDC-0094 (Requirement)
The Electric DC Motor of
the Hydraulic Actuator of Elevator shall be able to operate
at up to x Celsius degrees while in dynamic, unanticipated
atmospheric turbulence conditions.
- DeriveReqt -> SSL-HA-0049

## COL-EDC-0095 (Requirement)
The Electric DC Motor of
the Hydraulic Actuator of Elevator shall be able to operate
at up to x N∙m at y R.P.M. while in dynamic, unanticipated
atmospheric turbulence conditions.
- DeriveReqt -> SSL-HA-0055
- DeriveReqt -> SSL-HA-0056

## COL-FCC-0122 (Requirement)
The Feedback Control
Component shall be able to generate a control law capable of
reduce the gust effect by manipulating the Angle of Attack ensuring
n_z≤2 under all possible circumstances.
- DeriveReqt -> SSL-CONT-0107

## COL-FCC-0123 (Requirement)
The Feedback Control
Component shall be able to generate a control law capable of
reduce the gust effect by manipulating the Angle of Attack with a
maximum overshoot of 20% under all possible circumstances.
- DeriveReqt -> SSL-CONT-0107

## COL-FCC-0124 (Requirement)
The Feedback Control
Component shall be able to generate a control law capable of
reduce the gust effect by manipulating the Angle of Attack with a
maximum settling time of 20s under all possible
circumstances.
- DeriveReqt -> SSL-CONT-0107

## COL-FCC-0125 (Requirement)
The Feedback Control
Component shall be able to generate a control law capable of
reduce the gust effect by manipulating the Angle of Attack in such
a way the steady state error is reduced over time under all
possible circumstances.
- DeriveReqt -> SSL-CONT-0107

## COL-FIL-0100 (Requirement)
The Filter component shall filter the noise for the
controller input signals
- DeriveReqt -> SSL-CONT-0106

## COL-LAF-0113 (Requirement)
The Load Alleviation
Function shall be able to detect a gust and trigger the
control mechanism with a maximum delay of 0.5s under normal
conditions, unanticipated atmospheric gust conditions and/or the
failure or malfunctioning of one or more sensors.

## COL-LAF-0114 (Requirement)
The Load Alleviation
Function should obtain the Angle of Attack α from the
Flight Management System (which uses the SAC to calculate it),
which updates the value every 200ms under normal conditions,
unanticipated atmospheric gust conditions and/or the failure or
malfunctioning of one or more sensors.

## COL-SAC-0110 (Requirement)
The Sensor Array
Component shall be able to use measurements from sensors to
compute the vertical load factor of the Aircraft accounting for
Lift transient phenomena using a K_G=0.89 (see upstream
requirement) under normal conditions, unanticipated atmospheric
gust conditions and/or the failure or malfunctioning of one or more
sensors.

## COL-SAC-0111 (Requirement)
The Sensor Array
Component shall be able to use measurements from sensors to
compute the vertical load factor of the Aircraft accounting for
Lift transient phenomena using a W/S_w =650 kg/m^2
,C_lα=2π (see upstream requirement) under
normal conditions, unanticipated atmospheric gust conditions and/or
the failure or malfunctioning of one or more sensors.

## COL-SAC-0112 (Requirement)
The Sensor Array
Component shall be able to use measurements from sensors to
compute the vertical load factor of the Aircraft calculating the
density as a function of height ρ=ρ (h), using the
International Standard Atmosphere model (see upstream requirement)
under normal conditions, unanticipated atmospheric gust conditions
and/or the failure or malfunctioning of one or more sensors.

## COL-SAC-0115 (Requirement)
The Sensor Array
Component should be able to discriminate faulty measurements
from one sensor by using a median test under normal conditions,
unanticipated atmospheric gust conditions and/or the failure or
malfunctioning of one or more sensors.
- DeriveReqt -> SSL-CONT-0106

## COL-SAC-0116 (Requirement)
The Sensor Array
Component shall be able to provide a final measurement with
a maximum deviation of 0.2º and a confidence of 99% under
normal conditions, unanticipated atmospheric gust conditions and/or
the failure or malfunctioning of one or more sensors.
- DeriveReqt -> SSL-CONT-0106

## COL-SAC-0117 (Requirement)
The Sensor Array
Component shall be able to provide a final measurement with
a maximum deviation of 0.5º and a confidence of 90% under the
worst condition of failure of multiple sensors possible.
- DeriveReqt -> SSL-CONT-0106

## COL-SAC-0118 (Requirement)
The Sensor Array
Component shall have a maximum delay in its working sensors
bellow the one a first order transfer functions with time constant
equal to 0.02 would have under any circumstance.
- DeriveReqt -> SSL-CONT-0106

## COL-SAC-0119 (Requirement)
The Sensor Array
Component should be modeled by sensor with Gaussian noise
N(μ=0,σ=0.025) or a similar statistical function to be
added as noise.
- DeriveReqt -> SSL-CONT-0106

## COL-SAC-0134 (Requirement)
The controller
shall notify the Pilot when a defect is detected in the
HA

## COL-SAC-0136 (Requirement)
The difference between
actual and wanted motor speed shall converge to zero in X
seconds after a step change input in the omega_wanted position
command of Y rpm
- DeriveReqt -> SSL-CONT-0131

## COL-SAC-0137 (Requirement)
The speed controller
shall have a bandwidth of at least X dB
- DeriveReqt -> SSL-CONT-0131

## COL-SAC-0138 (Requirement)
The speed controller
shall determine a torque request for the motor in order to
reduce the difference between the speed of the motor and the wanted
speed of the motor
- DeriveReqt -> SSL-CONT-0131

## COL-SAC-0139 (Requirement)
The difference between
the wanted and actual elevator position shall converge to
zero in X seconds after a step change input in the
elevator_wanted_position command of Y degree
- DeriveReqt -> SSL-CONT-0132

## COL-SAC-0140 (Requirement)
The position controller
shall have a bandwidth of at least X dB
- DeriveReqt -> SSL-CONT-0132

## COL-SAC-0141 (Requirement)
The position controller
shall determine a wanted speed of the motor in order to
reduce the difference between the elevator position and the
elevator wanted position
- DeriveReqt -> SSL-CONT-0132
