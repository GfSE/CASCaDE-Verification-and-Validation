# A Model-Element with linked Requirement
- Rights: Creative Commons 4.0 CC BY-SA, https://creativecommons.org/licenses/by-sa/4.0/

## FiCo-Data (FMC:State)
- dcterms:description: Finance and Controlling Data, such as cost-units per project with budget, accrued cost etc.

## Data Volume (IREB:Requirement)
- dcterms:description: The data store MUST support a total volume up to 850 GB.
- SpecIF:Priority: SpecIF:priorityMedium

## Statements
- FiCo-Data oslc_rm:satisfies Data Volume
