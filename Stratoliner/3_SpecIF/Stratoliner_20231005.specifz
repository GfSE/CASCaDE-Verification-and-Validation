# Digital Data Package Dictionary
Includes 37 files

## Source file or resource (Source file or resource)

## Stratoliner_Actuator_Req.reqifz (Source file or resource)

## LOTAR_Manifest.xml (Source file or resource)

## Stratoliner_Actuator_Req.reqif (Source file or resource)

## Stratoliner_Actuator_Behavior.mdzip (Source file or resource)

## com.nomagic.magicdraw.uml_model.model (Source file or resource)

## proxy.local__PROJECT$h877558e9224f114d50dea1f39a1c119_resource_com$dnomagic$dci$dmetamodel$dproject$dsnapshot (Source file or resource)

## proxy.local__PROJECT$h9b4d2b1641e6203934d95e7bde5fe08_resource_com$dnomagic$dci$dmetamodel$dproject$dsnapshot (Source file or resource)

## proxy.local__PROJECT$hb818821ad5fb9956e13d5fa929369fcb_resource_com$dnomagic$dmagicdraw$duml_umodel$dshared_umodel$dsnapshot (Source file or resource)

## proxy.local__PROJECT$h44892a3bf693c0a47eb2f3bf10930f_resource_com$dnomagic$dmagicdraw$duml_umodel$dshared_umodel$dsnapshot (Source file or resource)

## BINARY-b9686d08-b167-4779-b696-f99c16766f90 (Source file or resource)

## proxy.local__PROJECT$h595f5a46$h4bbd$h4126$h86a6$hec01f155cb67_resource_com$dnomagic$dmagicdraw$duml_umodel$dshared_umodel$dsnapshot (Source file or resource)

## BINARY-28c50332-d794-4ef5-a89c-b95484b8029c (Source file or resource)

## BINARY-eb014b24-7581-4970-aba1-75976eeac700 (Source file or resource)

## Binaries.properties (Source file or resource)

## personal-Binaries.properties (Source file or resource)

## proxy.local__PROJECT$h44892a3bf693c0a47eb2f3bf10930f_resource_com$dnomagic$dci$dmetamodel$dproject$dsnapshot (Source file or resource)

## com.nomagic.magicdraw.core.project.options.commonprojectoptions (Source file or resource)

## PROJECT-7decaf17-48a2-4d6e-b214-85dd9630e7e6 (Source file or resource)

## personal-com.nomagic.magicdraw.core.project.options.personalprojectoptions (Source file or resource)

## BINARY-6ba8edcd-f50d-418d-87e1-01522e456e1f (Source file or resource)

## BINARY-a71ec3a6-11a6-4767-9799-e9c9321a42da (Source file or resource)

## com.nomagic.magicdraw.ce.dmn.commondmncodeengineering (Source file or resource)

## proxy.local__PROJECT$h595f5a46$h4bbd$h4126$h86a6$hec01f155cb67_resource_com$dnomagic$dci$dmetamodel$dproject$dsnapshot (Source file or resource)

## com.nomagic.ci.persistence.local.proxy.privatedependencylist (Source file or resource)

## proxy.local__PROJECT$h72379b04$h6dc6$h43b6$h8e2b$he79a5a6de142_resource_com$dnomagic$dci$dmetamodel$dproject$dsnapshot (Source file or resource)

## proxy.local__PROJECT$h9b4d2b1641e6203934d95e7bde5fe08_resource_com$dnomagic$dmagicdraw$duml_umodel$dshared_umodel$dsnapshot (Source file or resource)

## com.nomagic.ci.proxy.snapshot.descriptor.descriptors (Source file or resource)

## proxy.local__PROJECT$h72379b04$h6dc6$h43b6$h8e2b$he79a5a6de142_resource_com$dnomagic$dmagicdraw$duml_umodel$dshared_umodel$dsnapshot (Source file or resource)

## BINARY-5ed53398-0d82-4849-995d-e20a96407de3 (Source file or resource)

## proxy.local__PROJECT$h275116e7$h5669$h4796$h8d65$h3c2c8c8d3f9e_resource_com$dnomagic$dmagicdraw$duml_umodel$dshared_umodel$dsnapshot (Source file or resource)

## com.nomagic.ci.metamodel.project (Source file or resource)

## BINARY-def90731-ab39-4be6-a974-a2a3ab36cff0 (Source file or resource)

## proxy.local__PROJECT$hb818821ad5fb9956e13d5fa929369fcb_resource_com$dnomagic$dci$dmetamodel$dproject$dsnapshot (Source file or resource)

## com.nomagic.magicdraw.ce.commoncodeengineering (Source file or resource)

## proxy.local__PROJECT$h877558e9224f114d50dea1f39a1c119_resource_com$dnomagic$dmagicdraw$duml_umodel$dshared_umodel$dsnapshot (Source file or resource)

## proxy.local__PROJECT$h275116e7$h5669$h4796$h8d65$h3c2c8c8d3f9e_resource_com$dnomagic$dci$dmetamodel$dproject$dsnapshot (Source file or resource)

## Records.properties (Source file or resource)

## Comment (Comment)

## Person (Person)

## Michael Kirsch (Person)
- Identifier: kirsch
- Firstname: Michael
- Lastname: Kirsch
- Mail: michael.kirsch@em.ag

## EM-DA\kirsch (Person)

## Product Requirement (Product Requirement)

## SSL-CONT-0106 SSL-CONT-0106 (Product Requirement)
- Identifier: _19_0_3_56101ea_1582192244812_219194_43814
- Number: SSL-CONT-0106
- Title: SSL-CONT-0106
- Description: The Controller shall be able to sense and filter the
  Aircraft Angle of Attack under normal conditions, unanticipated
  atmospheric gust conditions and/or the failure or malfunctioning of
  one or more sensors.

## SSL-CONT-0107 SSL-CONT-0107 (Product Requirement)
- Identifier: _19_0_3_56101ea_1582195625213_763477_44084
- Number: SSL-CONT-0107
- Title: SSL-CONT-0107
- Description: The Controller shall be able to generate a control law
  capable of reduce the gust effect by manipulating the Angle of
  Attack ensuring structural integrity under all possible
  circumstances.

## SSL-CONT-0131 SSL-CONT-0131 (Product Requirement)
- Identifier: _19_0_3_62c020b_1582745990165_379645_42857
- Number: SSL-CONT-0131
- Title: SSL-CONT-0131
- Description: The controller
  shall have a speed control loop

## SSL-CONT-0132 SSL-CONT-0132 (Product Requirement)
- Identifier: _19_0_3_62c020b_1582746033529_866586_42868
- Number: SSL-CONT-0132
- Title: SSL-CONT-0132
- Description: The controller
  shall have a position control loop

## SSL-ELE-0021 SSL-ELE-0021 (Product Requirement)
- Identifier: _19_0_3_62c020b_1582744558522_462095_42506
- Number: SSL-ELE-0021
- Title: SSL-ELE-0021
- Description: The elevator
  should have a maximum planform area of x square
  meters.

## SSL-ELE-0022 SSL-ELE-0022 (Product Requirement)
- Identifier: _19_0_3_62c020b_1582744620860_856604_42523
- Number: SSL-ELE-0022
- Title: SSL-ELE-0022
- Description: The elevator
  should have a weight of less than x kilograms.

## SSL-ELE-0023 SSL-ELE-0023 (Product Requirement)
- Identifier: _19_0_3_62c020b_1582744659818_457350_42535
- Number: SSL-ELE-0023
- Title: SSL-ELE-0023
- Description: All the components or
  parts mounted on the elevator shall be able to operate under
  the power consumption restrictions resulting from dynamic,
  unanticipated atmospheric turbulence conditions as specified in
  ABD100.1.8,2.4.2 (or equivalent document).

## SSL-ELE-0024 SSL-ELE-0024 (Product Requirement)
- Identifier: _19_0_3_62c020b_1582744708481_715460_42547
- Number: SSL-ELE-0024
- Title: SSL-ELE-0024
- Description: All the components or
  parts mounted on the elevator shall operate according to
  RTCA/DO-160G.

## SSL-ELE-0039 SSL-ELE-0039 (Product Requirement)
- Identifier: _19_0_3_62c020b_1582745513515_654176_42755
- Number: SSL-ELE-0039
- Title: SSL-ELE-0039
- Description: The Elevator
  shall be able to operate under loads up to x lb (or other
  performance indicator) as specified in in FARxx (or corresponding
  standard) while in dynamic, unanticipated atmospheric turbulence
  conditions.

## SSL-ELE-0103 SSL-ELE-0103 (Product Requirement)
- Identifier: _19_0_3_62c020b_1582744918241_438917_42604
- Number: SSL-ELE-0103
- Title: SSL-ELE-0103
- Description: The Elevator control
  surfaces shall function ensuring the structural integrity of
  the aircraft and avoiding critical stall effects resulting from
  gust loads as specified in FAR 25.341 and 25.143 (or analogous EASA
  CS 25) while in dynamic, unanticipated atmospheric turbulence
  conditions.

## SSL-ELE-0200 SSL-ELE-0200 (Product Requirement)
- Identifier: _19_0_3_62c020b_1584541557867_82143_45449
- Number: SSL-ELE-0200
- Title: SSL-ELE-0200
- Description: The Elevator chord to tail chord ratio (CE /Ch) shall have a value
  from 0.2 to 0.4

## SSL-ELE-0201 SSL-ELE-0201 (Product Requirement)
- Identifier: _19_0_3_62c020b_1584541896494_351777_45456
- Number: SSL-ELE-0201
- Title: SSL-ELE-0201
- Description: The Elevator span to tail span ratio (bE/bh) shall have a value
  from 0.8 to 1

## SSL-ELE-0202 SSL-ELE-0202 (Product Requirement)
- Identifier: _19_0_3_62c020b_1584542164950_623395_45464
- Number: SSL-ELE-0202
- Title: SSL-ELE-0202
- Description: The Elevator maximum up elevator deflection (-Emax) shall be -25
  degrees

## SSL-ELE-0203 SSL-ELE-0203 (Product Requirement)
- Identifier: _19_0_3_62c020b_1584542617725_666769_45471
- Number: SSL-ELE-0203
- Title: SSL-ELE-0203
- Description: The Elevator maximum down elevator deflection (+Emax) shall be +20
  degrees

## SSL-ELE-0204 SSL-ELE-0204 (Product Requirement)
- Identifier: _19_0_3_62c020b_1584542746181_642823_45478
- Number: SSL-ELE-0204
- Title: SSL-ELE-0204
- Description: The Elevator planform area to horizontal tail planform area ratio
  (SE/Sh) shall have a value
  from 0.15 to 0.4

## SSL-HA-0043 SSL-HA-0043 (Product Requirement)
- Identifier: _19_0_3_62c020b_1582746078965_275977_42879
- Number: SSL-HA-0043
- Title: SSL-HA-0043
- Description: The Hydraulic Actuator
  of Elevator should have a length of less than x centimeters
  on its longest dimension when fully assembled.

## SSL-HA-0044 SSL-HA-0044 (Product Requirement)
- Identifier: _19_0_3_62c020b_1582746118206_119649_42891
- Number: SSL-HA-0044
- Title: SSL-HA-0044
- Description: The Hydraulic Actuator
  of Elevator should have a weight of less than x
  kilograms.

## SSL-HA-0045 SSL-HA-0045 (Product Requirement)
- Identifier: _19_0_3_62c020b_1582746158273_23675_42903
- Number: SSL-HA-0045
- Title: SSL-HA-0045
- Description: The Hydraulic Actuator
  of Elevator should have a volume of less than x cubic
  centimeters.

## SSL-HA-0049 SSL-HA-0049 (Product Requirement)
- Identifier: _19_0_3_62c020b_1582746341101_511238_42949
- Number: SSL-HA-0049
- Title: SSL-HA-0049
- Description: The Hydraulic Actuator
  of Elevator shall be able to operate in dynamic,
  unanticipated atmospheric turbulence conditions as specified in
  EUROCAE ED14 / RTCA/DO-160G Section 4.

## SSL-HA-0050 SSL-HA-0050 (Product Requirement)
- Identifier: _19_0_3_62c020b_1582746376074_403206_42961
- Number: SSL-HA-0050
- Title: SSL-HA-0050
- Description: The Hydraulic Actuator
  of Elevator shall be able to operate in variable temperature
  conditions as specified in RTCA/DO-160G Section 5.

## SSL-HA-0051 SSL-HA-0051 (Product Requirement)
- Identifier: _19_0_3_62c020b_1582746412830_674554_42972
- Number: SSL-HA-0051
- Title: SSL-HA-0051
- Description: The Hydraulic Actuator
  of Elevator shall be able to operate in humid atmospheres
  and anticipate adverse effects like corrosion or change of
  characteristics derived from the absorption of humidity as
  specified in RTCA/DO-160G Section 6.

## SSL-HA-0052 SSL-HA-0052 (Product Requirement)
- Identifier: _19_0_3_62c020b_1582746448871_89664_42983
- Number: SSL-HA-0052
- Title: SSL-HA-0052
- Description: The Hydraulic Actuator
  of Elevator shall be able to operate within performance
  standards after exposure to shocks experienced during normal
  aircraft operations, like taxiing, landing or when the aircraft
  encounters sudden gusts in a flight as specified in RTCA/DO-160G
  Section 7.

## SSL-HA-0053 SSL-HA-0053 (Product Requirement)
- Identifier: _19_0_3_62c020b_1582746485653_441678_42994
- Number: SSL-HA-0053
- Title: SSL-HA-0053
- Description: The Hydraulic Actuator
  of Elevator shall be able to operate under the operational
  vibrations resulting from dynamic, unanticipated atmospheric
  turbulence conditions as specified in RTCA/DO-160G Section
  8.

## SSL-HA-0054 SSL-HA-0054 (Product Requirement)
- Identifier: _19_0_3_62c020b_1582746524417_78057_43005
- Number: SSL-HA-0054
- Title: SSL-HA-0054
- Description: The Hydraulic Actuator
  of Elevator shall comply with the requirements and
  procedures for aircraft equipment that may come into contact with
  flammable fluids and vapors as specified in RTCA/DO-160G Section
  9.

## SSL-HA-0055 SSL-HA-0055 (Product Requirement)
- Identifier: _19_0_3_62c020b_1582746557208_765123_43016
- Number: SSL-HA-0055
- Title: SSL-HA-0055
- Description: The Hydraulic Actuator
  of Elevator shall be able to operate under the effects of
  liquids water being sprayed or falling on them or the effects of
  condensation as specified in RTCA/DO-160G Section 10.

## SSL-HA-0056 SSL-HA-0056 (Product Requirement)
- Identifier: _19_0_3_62c020b_1582746593950_9438_43027
- Number: SSL-HA-0056
- Title: SSL-HA-0056
- Description: The Hydraulic Actuator
  of Elevator shall be able to withstand the deleterious
  effects of fluid contaminants as specified in RTCA/DO-160G Section
  11.

## SSL-HA-0057 SSL-HA-0057 (Product Requirement)
- Identifier: _19_0_3_62c020b_1582746625755_140403_43038
- Number: SSL-HA-0057
- Title: SSL-HA-0057
- Description: The Hydraulic Actuator
  of Elevator shall be able to operate under the effects of
  blowing sand and dust where carried by air movement at moderate
  speeds as specified in RTCA/DO-160G Section 12.

## SSL-HA-0058 SSL-HA-0058 (Product Requirement)
- Identifier: _19_0_3_62c020b_1582746669568_775027_43049
- Number: SSL-HA-0058
- Title: SSL-HA-0058
- Description: The Hydraulic Actuator
  of Elevator shall not be adversely affected by fungi under
  conditions favorable for their development, namely, high humidity,
  warm atmosphere and presence of inorganic salts, as specified in
  RTCA/DO-160G Section 13.

## SSL-HA-0059 SSL-HA-0059 (Product Requirement)
- Identifier: _19_0_3_62c020b_1582746704731_818836_43060
- Number: SSL-HA-0059
- Title: SSL-HA-0059
- Description: The Hydraulic Actuator
  of Elevator shall anticipate the effects of prolonged
  exposure to a salt atmosphere or to salt fog experienced in normal
  operations, like corrosion of metals, clogging or binding of moving
  parts as a result of salt deposits, insulation fault or damage to
  contacts and uncoated wiring, as specified in RTCA/DO-160G Section
  14.

## SSL-HA-0060 SSL-HA-0060 (Product Requirement)
- Identifier: _19_0_3_62c020b_1582746738100_93535_43071
- Number: SSL-HA-0060
- Title: SSL-HA-0060
- Description: The Hydraulic Actuator
  of Elevator shall operate to operate within performance
  standards when exposed to icing conditions that would be
  encountered under conditions of rapid changes in temperature,
  altitude and humidity, as specified in RTCA/DO-160G Section
  24.

## SSL-HA-0061 SSL-HA-0061 (Product Requirement)
- Identifier: _19_0_3_62c020b_1582746775723_594251_43082
- Number: SSL-HA-0061
- Title: SSL-HA-0061
- Description: The Hydraulic Actuator
  of Elevator shall pass the tests conditions and procedure
  for Flammability and Fire resistance as specified in RTCA/DO-160G
  Section 26.

## SSL-HA-0062 SSL-HA-0062 (Product Requirement)
- Identifier: _19_0_3_62c020b_1582746813721_210274_43093
- Number: SSL-HA-0062
- Title: SSL-HA-0062
- Description: The Hydraulic Actuator
  of Elevator shall be able to operate under the power
  consumption restrictions resulting from dynamic, unanticipated
  atmospheric turbulence conditions as specified in ABD100.1.8,2.4.2
  (or equivalent document).

## SSL-HA-0077 SSL-HA-0077 (Product Requirement)
- Identifier: _19_0_3_62c020b_1582747429932_161232_43261
- Number: SSL-HA-0077
- Title: SSL-HA-0077
- Description: The Hydraulic Actuator
  of Elevator shall have a stroke of at least x
  millimeters.

## SSL-HA-0078 SSL-HA-0078 (Product Requirement)
- Identifier: _19_0_3_62c020b_1582747509967_241110_43282
- Number: SSL-HA-0078
- Title: SSL-HA-0078
- Description: The Hydraulic Actuator
  of Elevator shall be able to provide a minimum torque of x
  N∙m as specified in FARxx (or corresponding standard) while
  in dynamic, unanticipated atmospheric turbulence conditions.

## SSL-HA-0079 SSL-HA-0079 (Product Requirement)
- Identifier: _19_0_3_62c020b_1582747549653_92756_43294
- Number: SSL-HA-0079
- Title: SSL-HA-0079
- Description: The Hydraulic Actuator
  of Elevator shall be able to control the position of the
  Aileron with a precision of x% (or other performance indicator) as
  specified in FARxx (or corresponding standard) while in dynamic,
  unanticipated atmospheric turbulence conditions.

## SSL-HA-0080 SSL-HA-0080 (Product Requirement)
- Identifier: _19_0_3_62c020b_1582747598679_87717_43309
- Number: SSL-HA-0080
- Title: SSL-HA-0080
- Description: The Hydraulic Actuator
  of Elevator shall be able to control the speed of the
  Aileron with a precision of x% (or other performance indicator) as
  specified in FARxx (or corresponding standard) while in dynamic,
  unanticipated atmospheric turbulence conditions.

## SSL-HA-0081 SSL-HA-0081 (Product Requirement)
- Identifier: _19_0_3_62c020b_1582747651190_380197_43324
- Number: SSL-HA-0081
- Title: SSL-HA-0081
- Description: The Hydraulic Actuator
  of Elevator shall be able to operate up to x hours while in
  dynamic, unanticipated atmospheric turbulence conditions.

## Model (Product Requirement)
- Identifier: eee_1045467100313_135436_1

## 1 Power Supply Unit redundancy (Product Requirement)
- Identifier: _19_0_3_8e40285_1677089044368_946001_42767
- Number: 1
- Title: Power Supply Unit redundancy
- Description: Each Power Supply Unit must be able to power everything by its own.

## System Component (System Component)

## Model (System Component)
- Identifier: eee_1045467100313_135436_1
- Description: Author:kirsch.
  Created:10/1/12 3:10 PM.
  Title:.
  Comment:.

## System & Behavior (System Component)
- Identifier: _19_0_3_8e40285_1677088882355_726267_42602

## Power Supply Unit (System Component)
- Identifier: _19_0_3_8e40285_1677088927234_883192_42671

## Backup Power Supply Unit (System Component)
- Identifier: _19_0_3_8e40285_1677089023925_748779_42716

## (Auto)Pilot (System Component)
- Identifier: _19_0_3_8e40285_1677093578118_253732_42119

## PID (System Component)
- Identifier: _19_0_3_8e40285_1677093591284_915254_42164

## Motor (System Component)
- Identifier: _19_0_3_8e40285_1677095836086_121430_42209

## Actuator (System Component)
- Identifier: _19_0_3_8e40285_1677095852277_896738_42254

## Position Sensor (System Component)
- Identifier: _19_0_3_8e40285_1677095860293_77778_42299

## Speed Sensor (System Component)
- Identifier: _19_0_3_8e40285_1677095866364_730894_42344

## Load (System Component)
- Identifier: _19_0_3_8e40285_1677200751750_110679_43404

## Statements
- 1 Power Supply Unit redundancy part of Model
- System & Behavior part of Model
- Power Supply Unit part of System & Behavior
- Backup Power Supply Unit part of System & Behavior
- (Auto)Pilot part of System & Behavior
- PID part of System & Behavior
- Motor part of System & Behavior
- Actuator part of System & Behavior
- Position Sensor part of System & Behavior
- Speed Sensor part of System & Behavior
- Load part of System & Behavior
- SSL-CONT-0106 SSL-CONT-0106 Product Requirement is allocated to source document Stratoliner_Actuator_Req.reqif
- SSL-CONT-0107 SSL-CONT-0107 Product Requirement is allocated to source document Stratoliner_Actuator_Req.reqif
- SSL-CONT-0131 SSL-CONT-0131 Product Requirement is allocated to source document Stratoliner_Actuator_Req.reqif
- SSL-CONT-0132 SSL-CONT-0132 Product Requirement is allocated to source document Stratoliner_Actuator_Req.reqif
- SSL-ELE-0021 SSL-ELE-0021 Product Requirement is allocated to source document Stratoliner_Actuator_Req.reqif
- SSL-ELE-0022 SSL-ELE-0022 Product Requirement is allocated to source document Stratoliner_Actuator_Req.reqif
- SSL-ELE-0023 SSL-ELE-0023 Product Requirement is allocated to source document Stratoliner_Actuator_Req.reqif
- SSL-ELE-0024 SSL-ELE-0024 Product Requirement is allocated to source document Stratoliner_Actuator_Req.reqif
- SSL-ELE-0039 SSL-ELE-0039 Product Requirement is allocated to source document Stratoliner_Actuator_Req.reqif
- SSL-ELE-0103 SSL-ELE-0103 Product Requirement is allocated to source document Stratoliner_Actuator_Req.reqif
- SSL-ELE-0200 SSL-ELE-0200 Product Requirement is allocated to source document Stratoliner_Actuator_Req.reqif
- SSL-ELE-0201 SSL-ELE-0201 Product Requirement is allocated to source document Stratoliner_Actuator_Req.reqif
- SSL-ELE-0202 SSL-ELE-0202 Product Requirement is allocated to source document Stratoliner_Actuator_Req.reqif
- SSL-ELE-0203 SSL-ELE-0203 Product Requirement is allocated to source document Stratoliner_Actuator_Req.reqif
- SSL-ELE-0204 SSL-ELE-0204 Product Requirement is allocated to source document Stratoliner_Actuator_Req.reqif
- SSL-HA-0043 SSL-HA-0043 Product Requirement is allocated to source document Stratoliner_Actuator_Req.reqif
- SSL-HA-0044 SSL-HA-0044 Product Requirement is allocated to source document Stratoliner_Actuator_Req.reqif
- SSL-HA-0045 SSL-HA-0045 Product Requirement is allocated to source document Stratoliner_Actuator_Req.reqif
- SSL-HA-0049 SSL-HA-0049 Product Requirement is allocated to source document Stratoliner_Actuator_Req.reqif
- SSL-HA-0050 SSL-HA-0050 Product Requirement is allocated to source document Stratoliner_Actuator_Req.reqif
- SSL-HA-0051 SSL-HA-0051 Product Requirement is allocated to source document Stratoliner_Actuator_Req.reqif
- SSL-HA-0052 SSL-HA-0052 Product Requirement is allocated to source document Stratoliner_Actuator_Req.reqif
- SSL-HA-0053 SSL-HA-0053 Product Requirement is allocated to source document Stratoliner_Actuator_Req.reqif
- SSL-HA-0054 SSL-HA-0054 Product Requirement is allocated to source document Stratoliner_Actuator_Req.reqif
- SSL-HA-0055 SSL-HA-0055 Product Requirement is allocated to source document Stratoliner_Actuator_Req.reqif
- SSL-HA-0056 SSL-HA-0056 Product Requirement is allocated to source document Stratoliner_Actuator_Req.reqif
- SSL-HA-0057 SSL-HA-0057 Product Requirement is allocated to source document Stratoliner_Actuator_Req.reqif
- SSL-HA-0058 SSL-HA-0058 Product Requirement is allocated to source document Stratoliner_Actuator_Req.reqif
- SSL-HA-0059 SSL-HA-0059 Product Requirement is allocated to source document Stratoliner_Actuator_Req.reqif
- SSL-HA-0060 SSL-HA-0060 Product Requirement is allocated to source document Stratoliner_Actuator_Req.reqif
- SSL-HA-0061 SSL-HA-0061 Product Requirement is allocated to source document Stratoliner_Actuator_Req.reqif
- SSL-HA-0062 SSL-HA-0062 Product Requirement is allocated to source document Stratoliner_Actuator_Req.reqif
- SSL-HA-0077 SSL-HA-0077 Product Requirement is allocated to source document Stratoliner_Actuator_Req.reqif
- SSL-HA-0078 SSL-HA-0078 Product Requirement is allocated to source document Stratoliner_Actuator_Req.reqif
- SSL-HA-0079 SSL-HA-0079 Product Requirement is allocated to source document Stratoliner_Actuator_Req.reqif
- SSL-HA-0080 SSL-HA-0080 Product Requirement is allocated to source document Stratoliner_Actuator_Req.reqif
- SSL-HA-0081 SSL-HA-0081 Product Requirement is allocated to source document Stratoliner_Actuator_Req.reqif
- Model Product Requirement is allocated to source document com.nomagic.magicdraw.uml_model.model
- 1 Power Supply Unit redundancy Product Requirement is allocated to source document com.nomagic.magicdraw.uml_model.model
- Model System Component is allocated to source document com.nomagic.magicdraw.uml_model.model
- System & Behavior System Component is allocated to source document com.nomagic.magicdraw.uml_model.model
- Power Supply Unit System Component is allocated to source document com.nomagic.magicdraw.uml_model.model
- Backup Power Supply Unit System Component is allocated to source document com.nomagic.magicdraw.uml_model.model
- (Auto)Pilot System Component is allocated to source document com.nomagic.magicdraw.uml_model.model
- PID System Component is allocated to source document com.nomagic.magicdraw.uml_model.model
- Motor System Component is allocated to source document com.nomagic.magicdraw.uml_model.model
- Actuator System Component is allocated to source document com.nomagic.magicdraw.uml_model.model
- Position Sensor System Component is allocated to source document com.nomagic.magicdraw.uml_model.model
- Speed Sensor System Component is allocated to source document com.nomagic.magicdraw.uml_model.model
- Load System Component is allocated to source document com.nomagic.magicdraw.uml_model.model

## SSL-CONT-0106 (Requirement)
The Controller shall be able to sense and filter the
Aircraft Angle of Attack under normal conditions, unanticipated
atmospheric gust conditions and/or the failure or malfunctioning of
one or more sensors.

## SSL-CONT-0107 (Requirement)
The Controller shall be able to generate a control law
capable of reduce the gust effect by manipulating the Angle of
Attack ensuring structural integrity under all possible
circumstances.

## SSL-CONT-0131 (Requirement)
The controller
shall have a speed control loop
- DeriveReqt -> SSL-ELE-0103

## SSL-CONT-0132 (Requirement)
The controller
shall have a position control loop
- DeriveReqt -> SSL-ELE-0103
- DeriveReqt -> SSL-ELE-0103

## SSL-ELE-0021 (Requirement)
The elevator
should have a maximum planform area of x square
meters.

## SSL-ELE-0022 (Requirement)
The elevator
should have a weight of less than x kilograms.

## SSL-ELE-0023 (Requirement)
All the components or
parts mounted on the elevator shall be able to operate under
the power consumption restrictions resulting from dynamic,
unanticipated atmospheric turbulence conditions as specified in
ABD100.1.8,2.4.2 (or equivalent document).

## SSL-ELE-0024 (Requirement)
All the components or
parts mounted on the elevator shall operate according to
RTCA/DO-160G.

## SSL-ELE-0039 (Requirement)
The Elevator
shall be able to operate under loads up to x lb (or other
performance indicator) as specified in in FARxx (or corresponding
standard) while in dynamic, unanticipated atmospheric turbulence
conditions.

## SSL-ELE-0103 (Requirement)
The Elevator control
surfaces shall function ensuring the structural integrity of
the aircraft and avoiding critical stall effects resulting from
gust loads as specified in FAR 25.341 and 25.143 (or analogous EASA
CS 25) while in dynamic, unanticipated atmospheric turbulence
conditions.

## SSL-ELE-0200 (Design Constraint)
The Elevator chord to tail chord ratio (C_
E
/C_
h
) shall have a value
from 0.2 to 0.4

## SSL-ELE-0201 (Design Constraint)
The Elevator span to tail span ratio (b_
E
/b_
h
) shall have a value
from 0.8 to 1

## SSL-ELE-0202 (Design Constraint)
The Elevator maximum up elevator deflection (-
_Emax
) shall be -25
degrees

## SSL-ELE-0203 (Design Constraint)
The Elevator maximum down elevator deflection (+
_Emax
) shall be +20
degrees

## SSL-ELE-0204 (Design Constraint)
The Elevator planform area to horizontal tail planform area ratio
(S_
E
/S_
h
) shall have a value
from 0.15 to 0.4

## SSL-HA-0043 (Requirement)
The Hydraulic Actuator
of Elevator should have a length of less than x centimeters
on its longest dimension when fully assembled.

## SSL-HA-0044 (Requirement)
The Hydraulic Actuator
of Elevator should have a weight of less than x
kilograms.

## SSL-HA-0045 (Requirement)
The Hydraulic Actuator
of Elevator should have a volume of less than x cubic
centimeters.

## SSL-HA-0049 (Requirement)
The Hydraulic Actuator
of Elevator shall be able to operate in dynamic,
unanticipated atmospheric turbulence conditions as specified in
EUROCAE ED14 / RTCA/DO-160G Section 4.

## SSL-HA-0050 (Requirement)
The Hydraulic Actuator
of Elevator shall be able to operate in variable temperature
conditions as specified in RTCA/DO-160G Section 5.

## SSL-HA-0051 (Requirement)
The Hydraulic Actuator
of Elevator shall be able to operate in humid atmospheres
and anticipate adverse effects like corrosion or change of
characteristics derived from the absorption of humidity as
specified in RTCA/DO-160G Section 6.

## SSL-HA-0052 (Requirement)
The Hydraulic Actuator
of Elevator shall be able to operate within performance
standards after exposure to shocks experienced during normal
aircraft operations, like taxiing, landing or when the aircraft
encounters sudden gusts in a flight as specified in RTCA/DO-160G
Section 7.

## SSL-HA-0053 (Requirement)
The Hydraulic Actuator
of Elevator shall be able to operate under the operational
vibrations resulting from dynamic, unanticipated atmospheric
turbulence conditions as specified in RTCA/DO-160G Section
8.

## SSL-HA-0054 (Requirement)
The Hydraulic Actuator
of Elevator shall comply with the requirements and
procedures for aircraft equipment that may come into contact with
flammable fluids and vapors as specified in RTCA/DO-160G Section
9.

## SSL-HA-0055 (Requirement)
The Hydraulic Actuator
of Elevator shall be able to operate under the effects of
liquids water being sprayed or falling on them or the effects of
condensation as specified in RTCA/DO-160G Section 10.

## SSL-HA-0056 (Requirement)
The Hydraulic Actuator
of Elevator shall be able to withstand the deleterious
effects of fluid contaminants as specified in RTCA/DO-160G Section
11.

## SSL-HA-0057 (Requirement)
The Hydraulic Actuator
of Elevator shall be able to operate under the effects of
blowing sand and dust where carried by air movement at moderate
speeds as specified in RTCA/DO-160G Section 12.

## SSL-HA-0058 (Requirement)
The Hydraulic Actuator
of Elevator shall not be adversely affected by fungi under
conditions favorable for their development, namely, high humidity,
warm atmosphere and presence of inorganic salts, as specified in
RTCA/DO-160G Section 13.

## SSL-HA-0059 (Requirement)
The Hydraulic Actuator
of Elevator shall anticipate the effects of prolonged
exposure to a salt atmosphere or to salt fog experienced in normal
operations, like corrosion of metals, clogging or binding of moving
parts as a result of salt deposits, insulation fault or damage to
contacts and uncoated wiring, as specified in RTCA/DO-160G Section
14.

## SSL-HA-0060 (Requirement)
The Hydraulic Actuator
of Elevator shall operate to operate within performance
standards when exposed to icing conditions that would be
encountered under conditions of rapid changes in temperature,
altitude and humidity, as specified in RTCA/DO-160G Section
24.

## SSL-HA-0061 (Requirement)
The Hydraulic Actuator
of Elevator shall pass the tests conditions and procedure
for Flammability and Fire resistance as specified in RTCA/DO-160G
Section 26.

## SSL-HA-0062 (Requirement)
The Hydraulic Actuator
of Elevator shall be able to operate under the power
consumption restrictions resulting from dynamic, unanticipated
atmospheric turbulence conditions as specified in ABD100.1.8,2.4.2
(or equivalent document).

## SSL-HA-0077 (Requirement)
The Hydraulic Actuator
of Elevator shall have a stroke of at least x
millimeters.

## SSL-HA-0078 (Requirement)
The Hydraulic Actuator
of Elevator shall be able to provide a minimum torque of x
N∙m as specified in FARxx (or corresponding standard) while
in dynamic, unanticipated atmospheric turbulence conditions.

## SSL-HA-0079 (Requirement)
The Hydraulic Actuator
of Elevator shall be able to control the position of the
Aileron with a precision of x% (or other performance indicator) as
specified in FARxx (or corresponding standard) while in dynamic,
unanticipated atmospheric turbulence conditions.

## SSL-HA-0080 (Requirement)
The Hydraulic Actuator
of Elevator shall be able to control the speed of the
Aileron with a precision of x% (or other performance indicator) as
specified in FARxx (or corresponding standard) while in dynamic,
unanticipated atmospheric turbulence conditions.

## SSL-HA-0081 (Requirement)
The Hydraulic Actuator
of Elevator shall be able to operate up to x hours while in
dynamic, unanticipated atmospheric turbulence conditions.

## Notices in the file
Copyright © 2022 Boeing. All rights reserved
No license, LOTAR purposes
