# Small Autonomous Vehicle
A set of SpecIF Classes derived from a SpecIF Ontology for the domains SpecIF:DomainBase, SpecIF:DomainSystemsEngineering, SpecIF:DomainSystemModelIntegration.
- Rights: Creative Commons 4.0 CC BY-SA, https://creativecommons.org/licenses/by-sa/4.0/

## Small Autonomous Vehicle (SpecIF:Heading)
- dcterms:type: uml:Model

## 1. Requirements (uml:Package)
- dcterms:type: uml:Package

## Original Requirement Specification (pig:View)
- SpecIF:Diagram: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
- dcterms:type: uml:Diagram
- SpecIF:Notation: UML Requirement Diagram

## Navigation (IREB:Requirement)
- dcterms:type: uml:Class
- dcterms:description: The Vehicle shall autonomously choose the best route from the current location C to the target location T by means of a road map and actual traffic conditions.

## Road Driving (IREB:Requirement)
- dcterms:type: uml:Class
- dcterms:description: The vehicle shall be able to follow a selected road.

## Transport to Target (IREB:Requirement)
- dcterms:type: uml:Class
- dcterms:description: As a customer I would like to get a parcel delivered from the current location C to a target location T.

## Location as Postal Address (IREB:Requirement)
- dcterms:type: uml:Class
- dcterms:description: A location may be specified as a postal address.

## Obstacle Avoidance (IREB:Requirement)
- dcterms:type: uml:Class
- dcterms:description: The vehicle shall not hit a person or an obstacle on the road.

## Safe Driving (IREB:Requirement)
- dcterms:type: uml:Class
- dcterms:description: The vehicle shall drive no faster than allowed or adequate for the actual road condition.

## Loacation as GPS Coordinate (IREB:Requirement)
- dcterms:type: uml:Class
- dcterms:description: A location may be specified as GPS Coordinate with Longitude and Latitude in Degrees.

## 2. Functional Layer (uml:Package)
- dcterms:type: uml:Package

## Functional Decomposition (pig:View)
- SpecIF:Diagram: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
- dcterms:type: uml:Diagram
- SpecIF:Notation: SysML Block Definition Diagram

## Brake in an Emergency (SpecIF:ModelElement)
- dcterms:type: RFLP:Function
- dcterms:description: Take the vehicle to a full stop in the shortest time possible without loosing control over the trajectory.

## Set Speed (SpecIF:ModelElement)
- dcterms:type: RFLP:Function
- dcterms:description: The (autonomous) driver's speed command (gas pedal position).

## Turn Right (SpecIF:ModelElement)
- dcterms:type: RFLP:Function
- dcterms:description: Take a right turn at a road intersection. Observe the traffic entering the same lane and avoid a collision, if another vehicle does not observe the priority rules.

## Set Radius (SpecIF:ModelElement)
- dcterms:type: RFLP:Function
- dcterms:description: The (autonomous) driver's steering command (steering wheel position).

## Navigate (SpecIF:ModelElement)
- dcterms:type: RFLP:Function
- dcterms:description: Select a path to get from the current position to the target.

## Calculate Accelerations (SpecIF:ModelElement)
- dcterms:type: RFLP:Function

## Turn Left (SpecIF:ModelElement)
- dcterms:type: RFLP:Function
- dcterms:description: Take a left turn in a road intersection. Observe the priority rules and avoid traffic on the two lanes you are crossing.

## Drive to Target (SpecIF:ModelElement)
- dcterms:type: RFLP:Function
- dcterms:description: Manoevre the vehicle from the current position to the selected target.

## Set Acceleration Left (SpecIF:ModelElement)
- dcterms:type: RFLP:Function

## Select an adequate Speed (SpecIF:ModelElement)
- dcterms:type: RFLP:Function
- dcterms:description: Taking into account road condition and weather, select a safe speed.

## Set Acceleration Right (SpecIF:ModelElement)
- dcterms:type: RFLP:Function

## Follow the Road (SpecIF:ModelElement)
- dcterms:type: RFLP:Function
- dcterms:description: Keep the vehicle on the selected road.

## Apply Brake (SpecIF:ModelElement)
- dcterms:type: RFLP:Function

## 3. Logical Layer (uml:Package)
- dcterms:type: uml:Package

## Logical Decomposition (pig:View)
- SpecIF:Diagram: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
- dcterms:type: uml:Diagram
- SpecIF:Notation: SysML Block Definition Diagram

## Drive Right (SpecIF:ModelElement)
- dcterms:type: RFLP:Logical_System
- dcterms:description: The wheel with motor and brake on the right side. The motor can accelerate and decelerate. The motor controller is "4-quadrant" and can supply electrical current for recharging the batteries.

## Track Sensor (SpecIF:ModelElement)
- dcterms:type: RFLP:Logical_System

## Body (SpecIF:ModelElement)
- dcterms:type: RFLP:Logical_System

## Drive Left (SpecIF:ModelElement)
- dcterms:type: RFLP:Logical_System
- dcterms:description: The wheel with motor and brake on the left side. The motor can accelerate and decelerate. The motor controller is "4-quadrant" and can supply electrical current for recharging the batteries.

## LEGO Mindstorms Vehicle (SpecIF:ModelElement)
- dcterms:type: RFLP:Logical_System

## Support Front (SpecIF:ModelElement)
- dcterms:type: RFLP:Logical_System

## Controller (SpecIF:ModelElement)
- dcterms:type: RFLP:Logical_System

## Controller State Machine (pig:View)
- SpecIF:Diagram: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
- dcterms:type: uml:Diagram
- SpecIF:Notation: SysML State Machine Diagram

## entry (FMC:State)
- dcterms:type: uml:Pseudostate

## Off (FMC:State)
- dcterms:type: uml:State

## entry (FMC:State)
- dcterms:type: uml:Pseudostate

## Navigating (FMC:State)
- dcterms:type: uml:State

## Defining Target (FMC:State)
- dcterms:type: uml:State

## Following the Road (FMC:State)
- dcterms:type: uml:State

## Turning Right (FMC:State)
- dcterms:type: uml:State

## Turning Left (FMC:State)
- dcterms:type: uml:State

## Standing (FMC:State)
- dcterms:type: uml:State

## entry→Defining Target (FMC:Actor)
- dcterms:type: uml:Transition

## Defining Target→Navigating (FMC:Actor)
- dcterms:type: uml:Transition

## Navigating→Following the Road (FMC:Actor)
- dcterms:type: uml:Transition

## Following the Road→Navigating (FMC:Actor)
- dcterms:type: uml:Transition

## Following the Road→Turning Right (FMC:Actor)
- dcterms:type: uml:Transition

## Turning Right→Following the Road (FMC:Actor)
- dcterms:type: uml:Transition

## Following the Road→Turning Left (FMC:Actor)
- dcterms:type: uml:Transition

## Turning Left→Following the Road (FMC:Actor)
- dcterms:type: uml:Transition

## Following the Road→Standing (FMC:Actor)
- dcterms:type: uml:Transition

## Following the Road→Standing (FMC:Actor)
- dcterms:type: uml:Transition

## Standing→Following the Road (FMC:Actor)
- dcterms:type: uml:Transition

## Standing→Defining Target (FMC:Actor)
- dcterms:type: uml:Transition

## Standing→Off (FMC:Actor)
- dcterms:type: uml:Transition

## On (FMC:State)
- dcterms:type: uml:State

## entry→Off (FMC:Actor)
- dcterms:type: uml:Transition

## Off→On (FMC:Actor)
- dcterms:type: uml:Transition

## Support Rear (SpecIF:ModelElement)
- dcterms:type: RFLP:Logical_System

## Chassis (SpecIF:ModelElement)
- dcterms:type: RFLP:Logical_System

## Collision Alarm Sensor (SpecIF:ModelElement)
- dcterms:type: RFLP:Logical_System

## start_driving! (FMC:Event)
- dcterms:type: uml:SignalEvent

## turn_right! (FMC:Event)
- dcterms:type: uml:SignalEvent

## turned_right! (FMC:Event)
- dcterms:type: uml:SignalEvent

## turn_left! (FMC:Event)
- dcterms:type: uml:SignalEvent

## turned_left! (FMC:Event)
- dcterms:type: uml:SignalEvent

## switch_on! (FMC:Event)
- dcterms:type: uml:SignalEvent

## switch_off! (FMC:Event)
- dcterms:type: uml:SignalEvent

## continue_driving! (FMC:Event)
- dcterms:type: uml:SignalEvent

## halt! (FMC:Event)
- dcterms:type: uml:SignalEvent

## emergency_brake! (FMC:Event)
- dcterms:type: uml:SignalEvent

## navigate! (FMC:Event)
- dcterms:type: uml:SignalEvent

## new_target! (FMC:Event)
- dcterms:type: uml:SignalEvent

## re-navigate! (FMC:Event)
- dcterms:type: uml:CallEvent

## Model Elements (Glossary) (SpecIF:Heading)
- dcterms:type: SpecIF:Glossary

## Controller State Machine (FMC:Actor)
- dcterms:type: uml:StateMachine

## unnamed uml:Region (FMC:Actor)
- dcterms:type: uml:Region

## unnamed uml:Region (FMC:Actor)
- dcterms:type: uml:Region

## Statements
- 1. Requirements SpecIF:contains Original Requirement Specification
- 1. Requirements SpecIF:contains Navigation
- 1. Requirements SpecIF:contains Road Driving
- 1. Requirements SpecIF:contains Transport to Target
- 1. Requirements SpecIF:contains Location as Postal Address
- 1. Requirements SpecIF:contains Obstacle Avoidance
- 1. Requirements SpecIF:contains Safe Driving
- 1. Requirements SpecIF:contains Loacation as GPS Coordinate
- 2. Functional Layer SpecIF:contains Functional Decomposition
- 2. Functional Layer SpecIF:contains Brake in an Emergency
- 2. Functional Layer SpecIF:contains Set Speed
- 2. Functional Layer SpecIF:contains Turn Right
- 2. Functional Layer SpecIF:contains Set Radius
- 2. Functional Layer SpecIF:contains Navigate
- 2. Functional Layer SpecIF:contains Calculate Accelerations
- 2. Functional Layer SpecIF:contains Turn Left
- 2. Functional Layer SpecIF:contains Drive to Target
- 2. Functional Layer SpecIF:contains Set Acceleration Left
- 2. Functional Layer SpecIF:contains Select an adequate Speed
- 2. Functional Layer SpecIF:contains Set Acceleration Right
- 2. Functional Layer SpecIF:contains Follow the Road
- 2. Functional Layer SpecIF:contains Apply Brake
- Follow the Road dcterms:hasPart Set Radius
- Brake in an Emergency dcterms:hasPart Calculate Accelerations
- Calculate Accelerations dcterms:hasPart Set Acceleration Right
- Turn Left dcterms:hasPart Set Radius
- Drive to Target dcterms:hasPart Turn Left
- Drive to Target dcterms:hasPart Turn Right
- Drive to Target dcterms:hasPart Brake in an Emergency
- Turn Right dcterms:hasPart Set Radius
- Turn Right dcterms:hasPart Select an adequate Speed
- Set Speed dcterms:hasPart Calculate Accelerations
- Calculate Accelerations dcterms:hasPart Apply Brake
- Turn Left dcterms:hasPart Select an adequate Speed
- Follow the Road dcterms:hasPart Select an adequate Speed
- Drive to Target dcterms:hasPart Navigate
- Select an adequate Speed dcterms:hasPart Set Speed
- Set Radius dcterms:hasPart Calculate Accelerations
- Drive to Target dcterms:hasPart Follow the Road
- Calculate Accelerations dcterms:hasPart Set Acceleration Left
- 3. Logical Layer SpecIF:contains Logical Decomposition
- 3. Logical Layer SpecIF:contains Drive Right
- 3. Logical Layer SpecIF:contains Track Sensor
- 3. Logical Layer SpecIF:contains Body
- 3. Logical Layer SpecIF:contains Drive Left
- 3. Logical Layer SpecIF:contains LEGO Mindstorms Vehicle
- 3. Logical Layer SpecIF:contains Support Front
- 3. Logical Layer SpecIF:contains Controller
- Controller uml:ownedBehavior Controller State Machine
- 3. Logical Layer SpecIF:contains Controller State Machine
- 3. Logical Layer SpecIF:contains Controller State Machine
- Controller State Machine uml:ownedDiagram Controller State Machine
- Controller State Machine SpecIF:contains unnamed uml:Region
- unnamed uml:Region SpecIF:contains entry
- unnamed uml:Region SpecIF:contains Off
- unnamed uml:Region SpecIF:contains On
- On SpecIF:contains unnamed uml:Region
- unnamed uml:Region SpecIF:contains entry
- unnamed uml:Region SpecIF:contains Navigating
- unnamed uml:Region SpecIF:contains Defining Target
- unnamed uml:Region SpecIF:contains Following the Road
- unnamed uml:Region SpecIF:contains Turning Right
- unnamed uml:Region SpecIF:contains Turning Left
- unnamed uml:Region SpecIF:contains Standing
- entry→Defining Target uml:TransitionSource entry
- entry→Defining Target uml:TransitionTarget Defining Target
- Defining Target→Navigating uml:TransitionSource Defining Target
- Defining Target→Navigating uml:TransitionTarget Navigating
- navigate! uml:Trigger Defining Target→Navigating
- Navigating→Following the Road uml:TransitionSource Navigating
- Navigating→Following the Road uml:TransitionTarget Following the Road
- start_driving! uml:Trigger Navigating→Following the Road
- Following the Road→Navigating uml:TransitionSource Following the Road
- Following the Road→Navigating uml:TransitionTarget Navigating
- re-navigate! uml:Trigger Following the Road→Navigating
- Following the Road→Turning Right uml:TransitionSource Following the Road
- Following the Road→Turning Right uml:TransitionTarget Turning Right
- turn_right! uml:Trigger Following the Road→Turning Right
- Turning Right→Following the Road uml:TransitionSource Turning Right
- Turning Right→Following the Road uml:TransitionTarget Following the Road
- turned_right! uml:Trigger Turning Right→Following the Road
- Following the Road→Turning Left uml:TransitionSource Following the Road
- Following the Road→Turning Left uml:TransitionTarget Turning Left
- turn_left! uml:Trigger Following the Road→Turning Left
- Turning Left→Following the Road uml:TransitionSource Turning Left
- Turning Left→Following the Road uml:TransitionTarget Following the Road
- turned_left! uml:Trigger Turning Left→Following the Road
- Following the Road→Standing uml:TransitionSource Following the Road
- Following the Road→Standing uml:TransitionTarget Standing
- halt! uml:Trigger Following the Road→Standing
- Following the Road→Standing uml:TransitionSource Following the Road
- Following the Road→Standing uml:TransitionTarget Standing
- emergency_brake! uml:Trigger Following the Road→Standing
- Standing→Following the Road uml:TransitionSource Standing
- Standing→Following the Road uml:TransitionTarget Following the Road
- continue_driving! uml:Trigger Standing→Following the Road
- Standing→Defining Target uml:TransitionSource Standing
- Standing→Defining Target uml:TransitionTarget Defining Target
- new_target! uml:Trigger Standing→Defining Target
- Standing→Off uml:TransitionSource Standing
- Standing→Off uml:TransitionTarget Off
- switch_off! uml:Trigger Standing→Off
- entry→Off uml:TransitionSource entry
- entry→Off uml:TransitionTarget Off
- Off→On uml:TransitionSource Off
- Off→On uml:TransitionTarget On
- switch_on! uml:Trigger Off→On
- 3. Logical Layer SpecIF:contains Support Rear
- 3. Logical Layer SpecIF:contains Chassis
- 3. Logical Layer SpecIF:contains Collision Alarm Sensor
- 3. Logical Layer SpecIF:contains start_driving!
- 3. Logical Layer SpecIF:contains turn_right!
- 3. Logical Layer SpecIF:contains turned_right!
- 3. Logical Layer SpecIF:contains turn_left!
- 3. Logical Layer SpecIF:contains turned_left!
- 3. Logical Layer SpecIF:contains switch_on!
- 3. Logical Layer SpecIF:contains switch_off!
- 3. Logical Layer SpecIF:contains continue_driving!
- 3. Logical Layer SpecIF:contains halt!
- 3. Logical Layer SpecIF:contains emergency_brake!
- 3. Logical Layer SpecIF:contains navigate!
- 3. Logical Layer SpecIF:contains new_target!
- 3. Logical Layer SpecIF:contains re-navigate!
- LEGO Mindstorms Vehicle dcterms:hasPart Controller
- LEGO Mindstorms Vehicle dcterms:hasPart Collision Alarm Sensor
- LEGO Mindstorms Vehicle dcterms:hasPart Chassis
- LEGO Mindstorms Vehicle dcterms:hasPart Drive Right
- LEGO Mindstorms Vehicle dcterms:hasPart Body
- LEGO Mindstorms Vehicle dcterms:hasPart Track Sensor
- LEGO Mindstorms Vehicle dcterms:hasPart Support Front
- LEGO Mindstorms Vehicle dcterms:hasPart Support Rear
- LEGO Mindstorms Vehicle dcterms:hasPart Drive Left
- Navigation IREB:refines Transport to Target
- Safe Driving IREB:refines Transport to Target
- Location as Postal Address IREB:refines Transport to Target
- Obstacle Avoidance IREB:refines Transport to Target
- Loacation as GPS Coordinate IREB:refines Transport to Target
- Road Driving IREB:refines Transport to Target
- Follow the Road oslc_rm:satisfies Road Driving
- Navigate oslc_rm:satisfies Navigation
- Calculate Accelerations sysml:Allocate Controller
- Apply Brake sysml:Allocate Drive Left
- Set Acceleration Right sysml:Allocate Drive Right
- Set Acceleration Left sysml:Allocate Drive Left
- Select an adequate Speed oslc_rm:satisfies Safe Driving
- Apply Brake sysml:Allocate Drive Right
- Original Requirement Specification SpecIF:shows Road Driving
- Original Requirement Specification SpecIF:shows Safe Driving
- Original Requirement Specification SpecIF:shows Navigation
- Original Requirement Specification SpecIF:shows Obstacle Avoidance
- Original Requirement Specification SpecIF:shows Transport to Target
- Original Requirement Specification SpecIF:shows Loacation as GPS Coordinate
- Original Requirement Specification SpecIF:shows Location as Postal Address
- Functional Decomposition SpecIF:shows Controller
- Functional Decomposition SpecIF:shows Follow the Road
- Functional Decomposition SpecIF:shows Set Acceleration Right
- Functional Decomposition SpecIF:shows Calculate Accelerations
- Functional Decomposition SpecIF:shows Turn Right
- Functional Decomposition SpecIF:shows Drive to Target
- Functional Decomposition SpecIF:shows Navigate
- Functional Decomposition SpecIF:shows Brake in an Emergency
- Functional Decomposition SpecIF:shows Safe Driving
- Functional Decomposition SpecIF:shows Navigation
- Functional Decomposition SpecIF:shows Turn Left
- Functional Decomposition SpecIF:shows Set Radius
- Functional Decomposition SpecIF:shows Set Acceleration Left
- Functional Decomposition SpecIF:shows Drive Right
- Functional Decomposition SpecIF:shows Road Driving
- Functional Decomposition SpecIF:shows Set Speed
- Functional Decomposition SpecIF:shows Select an adequate Speed
- Functional Decomposition SpecIF:shows Drive Left
- Functional Decomposition SpecIF:shows Apply Brake
- Logical Decomposition SpecIF:shows Controller
- Logical Decomposition SpecIF:shows Support Front
- Logical Decomposition SpecIF:shows Drive Right
- Logical Decomposition SpecIF:shows Collision Alarm Sensor
- Logical Decomposition SpecIF:shows Body
- Logical Decomposition SpecIF:shows Chassis
- Logical Decomposition SpecIF:shows Track Sensor
- Logical Decomposition SpecIF:shows Support Rear
- Logical Decomposition SpecIF:shows LEGO Mindstorms Vehicle
- Logical Decomposition SpecIF:shows Drive Left
- Controller State Machine SpecIF:shows Navigating
- Controller State Machine SpecIF:shows Turning Left→Following the Road
- Controller State Machine SpecIF:shows entry
- Controller State Machine SpecIF:shows Defining Target→Navigating
- Controller State Machine SpecIF:shows Following the Road→Turning Right
- Controller State Machine SpecIF:shows Turning Right→Following the Road
- Controller State Machine SpecIF:shows Standing
- Controller State Machine SpecIF:shows Turning Right
- Controller State Machine SpecIF:shows Off
- Controller State Machine SpecIF:shows Off→On
- Controller State Machine SpecIF:shows Following the Road→Turning Left
- Controller State Machine SpecIF:shows entry→Off
- Controller State Machine SpecIF:shows entry
- Controller State Machine SpecIF:shows On
- Controller State Machine SpecIF:shows Standing→Defining Target
- Controller State Machine SpecIF:shows entry→Defining Target
- Controller State Machine SpecIF:shows Following the Road
- Controller State Machine SpecIF:shows Standing→Following the Road
- Controller State Machine SpecIF:shows Following the Road→Standing
- Controller State Machine SpecIF:shows Navigating→Following the Road
- Controller State Machine SpecIF:shows Following the Road→Navigating
- Controller State Machine SpecIF:shows Defining Target
- Controller State Machine SpecIF:shows Standing→Off
- Controller State Machine SpecIF:shows Following the Road→Standing
- Controller State Machine SpecIF:shows unnamed uml:Region
- Controller State Machine SpecIF:shows Turning Left
- Controller State Machine SpecIF:shows Controller State Machine
- Controller State Machine SpecIF:shows unnamed uml:Region
- Controller State Machine SpecIF:shows navigate!
- Controller State Machine SpecIF:shows start_driving!
- Controller State Machine SpecIF:shows re-navigate!
- Controller State Machine SpecIF:shows turn_right!
- Controller State Machine SpecIF:shows turned_right!
- Controller State Machine SpecIF:shows turn_left!
- Controller State Machine SpecIF:shows turned_left!
- Controller State Machine SpecIF:shows halt!
- Controller State Machine SpecIF:shows emergency_brake!
- Controller State Machine SpecIF:shows continue_driving!
- Controller State Machine SpecIF:shows new_target!
- Controller State Machine SpecIF:shows switch_off!
- Controller State Machine SpecIF:shows switch_on!
