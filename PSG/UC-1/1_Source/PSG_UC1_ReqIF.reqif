## REQ-OR-1: OR-1
- The S system shall provide an operator interface that
  displays available imaging modes and their key parameters
  (frequency, resolution, coverage, DF, power).
- I, D

## REQ-OR-2: OR-2
- The system shall allow operators to pre-plan sequences of
  modes along the flight path.
- D, I

## REQ-OR-3: OR-3
- The system shall support in-mission re-tasking of modes
  subject to platform and resource constraints.
- D, T

## REQ-OR-4: OR-4
- The system shall enforce safety and resource constraints
  (e.g., maximum duty cycle, power limits) when selecting
  high-demand zoom modes.
- A, T

## REQ-OR-5: OR-5
- The system shall log all mode selections, wavelength
  settings, and associated metadata for post-mission analysis
  and verification.
- I, T

## REQ-OR-6: OR-6
- The system shall provide health and status indicators for
  RF subsystems, timing, and processing relevant to all
  wavelength modes.
- I, T

## REQ-OR-7: OR-7
- The system shall support automatic mode selection policies
  where required by the concept of operations.
- A, D
