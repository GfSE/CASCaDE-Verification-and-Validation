# SYSMOD
A set of SpecIF Classes derived from a SpecIF Ontology for the domains SpecIF:DomainBase, SpecIF:DomainSystemsEngineering, SpecIF:DomainSystemModelIntegration.
- Rights: Creative Commons 4.0 CC BY-SA, https://creativecommons.org/licenses/by-sa/4.0/

## SYSMOD (SpecIF:Heading)
- dcterms:description: SYSMOD, version 4.2beta

  MBSE4U - Tim Weilkiens, http://www.mbse4u.com
  Detailed description of SYSMOD: http://leanpub.com/sysmod

  Copyright 2017 Tim Weilkiens

  Licensed under the Apache License, Version 2.0 (the "License");
  you may not use this file except in compliance with the License.
  You may obtain a copy of the License at

      http://www.apache.org/licenses/LICENSE-2.0

  Unless required by applicable law or agreed to in writing, software
  distributed under the License is distributed on an "AS IS" BASIS,
  WITHOUT WARRANTIES OR CONDITIONS OF ANY KIND, either express or implied.
  See the License for the specific language governing permissions and
  limitations under the License.
- dcterms:type: uml:Profile

## Actors (uml:Package)
- dcterms:type: uml:Package

## Actor stereotypes (SpecIF:View)
- dcterms:type: uml:Diagram
- SpecIF:Notation: SysML Package Diagram

## Blocks (uml:Package)
- dcterms:type: uml:Package

## Block stereotypes (SpecIF:View)
- dcterms:type: uml:Diagram
- SpecIF:Notation: SysML Block Definition Diagram

## VAMOS (uml:Package)
- dcterms:type: uml:Package
- dcterms:description: VAriant MOdeling with SysML (VAMOS)
  The method is described in the book
  Tim Weilkiens. Variant Modeling wih SysML. MBSE4U - Tim Weilkiens. 2016.
  https://leanpub.com/variantmodelingwithsysml

## BindingTimeKind (SpecIF:View)
- dcterms:type: uml:Diagram
- SpecIF:Notation: SysML Package Diagram

## REQUIRES constraint (SpecIF:View)
- dcterms:type: uml:Diagram
- SpecIF:Notation: SysML Package Diagram

## Variant (SpecIF:View)
- dcterms:type: uml:Diagram
- SpecIF:Notation: SysML Package Diagram

## Variant configuration (SpecIF:View)
- dcterms:type: uml:Diagram
- SpecIF:Notation: SysML Package Diagram

## Variation point (SpecIF:View)
- dcterms:type: uml:Diagram
- SpecIF:Notation: SysML Package Diagram

## Variation (SpecIF:View)
- dcterms:type: uml:Diagram
- SpecIF:Notation: SysML Package Diagram

## XOR constraint (SpecIF:View)
- dcterms:type: uml:Diagram
- SpecIF:Notation: SysML Package Diagram

## Variant stereotypes (SpecIF:View)
- dcterms:type: uml:Diagram
- SpecIF:Notation: SysML Package Diagram

## VAMOS Validation Suite (uml:Package)
- dcterms:type: uml:Package

## Requirements (uml:Package)
- dcterms:type: uml:Package

## Requirements stereotypes (SpecIF:View)
- dcterms:type: uml:Diagram
- SpecIF:Notation: SysML Package Diagram

## Text-based requirements (uml:Package)
- dcterms:type: uml:Package
- dcterms:description: Text-based requirements are introducted to enable placing the requirement model elements in the toolbar of the modeling tool. Without a concrete metaclass like Class, the tool cannot create a model element.

## Text-based requirements (SpecIF:View)
- dcterms:type: uml:Diagram
- SpecIF:Notation: UML Generic Table

## Non-text-based requirements (uml:Package)
- dcterms:type: uml:Package

## Non-text-based requirements (SpecIF:View)
- dcterms:type: uml:Diagram
- SpecIF:Notation: SysML Package Diagram

## Disciplines (uml:Package)
- dcterms:type: uml:Package

## Discipline Stereotypes (SpecIF:View)
- dcterms:type: uml:Diagram
- SpecIF:Notation: SysML Block Definition Diagram

## Activities (uml:Package)
- dcterms:type: uml:Package

## Activity stereotypes (SpecIF:View)
- dcterms:type: uml:Diagram
- SpecIF:Notation: SysML Block Definition Diagram

## Relationships (uml:Package)
- dcterms:type: uml:Package
- dcterms:description: deprecated since SysML 1.6

## Relationship stereotypes (SpecIF:View)
- dcterms:type: uml:Diagram
- SpecIF:Notation: SysML Package Diagram

## SYSMOD Validation Suite (uml:Package)
- dcterms:type: uml:Package

## Verification (uml:Package)
- dcterms:type: uml:Package

## Verification stereotypes (SpecIF:View)
- dcterms:type: uml:Diagram
- SpecIF:Notation: SysML Package Diagram

## UseCases (uml:Package)
- dcterms:type: uml:Package

## Use case stereotypes (SpecIF:View)
- dcterms:type: uml:Diagram
- SpecIF:Notation: SysML Package Diagram

## Enumerations (uml:Package)
- dcterms:type: uml:Package

## SYSMOD enumerations (SpecIF:View)
- dcterms:type: uml:Diagram
- SpecIF:Notation: SysML Block Definition Diagram

## SYSMOD-v4.2 (SpecIF:Heading)
- dcterms:description: SYSMOD - The Systems Modeling Toolbox, Version 4.2
  https://leanpub.com/sysmod
  https://www.mbse4u.com
  Copyright 2020 Tim Weilkiens
  Licensed under the Apache License, Version 2.0 (the "License");
  you may not use this file except in compliance with the License.
  You may obtain a copy of the License at
  http://www.apache.org/licenses/LICENSE-2.0
  Unless required by applicable law or agreed to in writing, software
  distributed under the License is distributed on an "AS IS" BASIS,
  WITHOUT WARRANTIES OR CONDITIONS OF ANY KIND, either express or implied.
  See the License for the specific language governing permissions and
  limitations under the License.
- dcterms:type: uml:Model

## SYSMOD Profile Overview (SpecIF:View)
- dcterms:type: uml:Diagram
- SpecIF:Notation: UML Class Diagram

## Open Issues (SpecIF:View)
- dcterms:type: uml:Diagram
- SpecIF:Notation: UML Generic Table

## Model Elements (Glossary) (SpecIF:Heading)
- dcterms:type: SpecIF:Glossary

## Statements
- Actors SpecIF:contains Actor stereotypes
- Blocks SpecIF:contains Block stereotypes
- VAMOS SpecIF:contains BindingTimeKind
- VAMOS SpecIF:contains REQUIRES constraint
- VAMOS SpecIF:contains Variant
- VAMOS SpecIF:contains Variant configuration
- VAMOS SpecIF:contains Variation point
- VAMOS SpecIF:contains Variation
- VAMOS SpecIF:contains XOR constraint
- VAMOS SpecIF:contains Variant stereotypes
- Requirements SpecIF:contains Requirements stereotypes
- Text-based requirements SpecIF:contains Text-based requirements
- Non-text-based requirements SpecIF:contains Non-text-based requirements
- Disciplines SpecIF:contains Discipline Stereotypes
- Activities SpecIF:contains Activity stereotypes
- Relationships SpecIF:contains Relationship stereotypes
- Verification SpecIF:contains Verification stereotypes
- UseCases SpecIF:contains Use case stereotypes
- Enumerations SpecIF:contains SYSMOD enumerations
