# Model
A set of SpecIF Classes derived from a SpecIF Ontology for the domains SpecIF:DomainBase, SpecIF:DomainSystemsEngineering, SpecIF:DomainSystemModelIntegration.
- Rights: Creative Commons 4.0 CC BY-SA, https://creativecommons.org/licenses/by-sa/4.0/

## Acceleration (SpecIF:ModelElement)
- dcterms:type: sysml:Block

## RFLP Profile (SpecIF:View)
- SpecIF:Diagram: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
- dcterms:type: uml:Diagram
- SpecIF:Notation: Profile Diagram

## Original Requirement Specification (SpecIF:View)
- SpecIF:Diagram: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
- dcterms:type: uml:Diagram
- SpecIF:Notation: Requirement Diagram

## Transport to Target (SpecIF:ModelElement)
- dcterms:type: sysml:Requirement

## Navigation (SpecIF:ModelElement)
- dcterms:type: sysml:Requirement

## Road Driving (SpecIF:ModelElement)
- dcterms:type: sysml:Requirement

## Safe Driving (SpecIF:ModelElement)
- dcterms:type: sysml:Requirement

## Obstacle Avoidance (SpecIF:ModelElement)
- dcterms:type: sysml:Requirement

## Location as Postal Address (SpecIF:ModelElement)
- dcterms:type: sysml:Requirement

## Loacation as GPS Coordinate (SpecIF:ModelElement)
- dcterms:type: sysml:Requirement

## Functional Decomposition (SpecIF:View)
- SpecIF:Diagram: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
- dcterms:type: uml:Diagram
- SpecIF:Notation: SysML Block Definition Diagram

## Drive to Target (SpecIF:ModelElement)
- dcterms:type: RFLP:Function
- dcterms:description: Manoevre the vehicle from the current position to the selected target.

## Navigate (SpecIF:ModelElement)
- dcterms:type: RFLP:Function
- dcterms:description: Select a path to get from the current position to the target.

## Follow the Road (SpecIF:ModelElement)
- dcterms:type: RFLP:Function
- dcterms:description: Keep the vehicle on the selected road.

## Select an adequate Speed (SpecIF:ModelElement)
- dcterms:type: RFLP:Function
- dcterms:description: Taking into account road condition and weather, select a safe speed.

## Brake in an Emergency (SpecIF:ModelElement)
- dcterms:type: RFLP:Function
- dcterms:description: Take the vehicle to a full stop in the shortest time possible without loosing control over the trajectory.

## Set Radius (SpecIF:ModelElement)
- dcterms:type: RFLP:Function
- dcterms:description: The (autonomous) driver's steering command (steering wheel position).

## Set Speed (SpecIF:ModelElement)
- dcterms:type: RFLP:Function
- dcterms:description: The (autonomous) driver's speed command (gas pedal position).

## Set Acceleration Left (SpecIF:ModelElement)
- dcterms:type: RFLP:Function

## Set Acceleration Right (SpecIF:ModelElement)
- dcterms:type: RFLP:Function

## Calculate Accelerations (SpecIF:ModelElement)
- dcterms:type: RFLP:Function

## Turn Right (SpecIF:ModelElement)
- dcterms:type: RFLP:Function
- dcterms:description: Take a right turn at a road intersection. Observe the traffic entering the same lane and avoid a collision, if another vehicle does not observe the priority rules.

## Turn Left (SpecIF:ModelElement)
- dcterms:type: RFLP:Function
- dcterms:description: Take a left turn in a road intersection. Observe the priority rules and avoid traffic on the two lanes you are crossing.

## Apply Brake (SpecIF:ModelElement)
- dcterms:type: RFLP:Function

## Physical Decomposition (SpecIF:View)
- dcterms:type: uml:Diagram
- SpecIF:Notation: SysML Block Definition Diagram

## LEGO Mindstorms Set (uml:Package)
- dcterms:type: uml:Package
- dcterms:description: The wheel with motor and brake on the left side. The motor can accelerate and decelerate. The motor controller is "4-quadrant" and can supply electrical current for recharging the batteries.

## LEGO Mindstorms Vehicle (SpecIF:ModelElement)
- dcterms:type: RFLP:System

## Chassis (SpecIF:ModelElement)
- dcterms:type: RFLP:Component

## Body (SpecIF:ModelElement)
- dcterms:type: RFLP:Component

## Drive Left (SpecIF:ModelElement)
- dcterms:type: RFLP:Component
- dcterms:description: The wheel with motor and brake on the left side. The motor can accelerate and decelerate. The motor controller is "4-quadrant" and can supply electrical current for recharging the batteries.

## Support Front (SpecIF:ModelElement)
- dcterms:type: RFLP:Component

## Support Rear (SpecIF:ModelElement)
- dcterms:type: RFLP:Component

## Controller (SpecIF:ModelElement)
- dcterms:type: RFLP:Component

## Track Sensor (SpecIF:ModelElement)
- dcterms:type: RFLP:Component

## Collision Alarm Sensor (SpecIF:ModelElement)
- dcterms:type: RFLP:Component

## Drive Right (SpecIF:ModelElement)
- dcterms:type: RFLP:Component
- dcterms:description: The wheel with motor and brake on the right side. The motor can accelerate and decelerate. The motor controller is "4-quadrant" and can supply electrical current for recharging the batteries.

## Model Elements (Glossary) (SpecIF:Heading)
- dcterms:type: SpecIF:Glossary

## Statements
- LEGO Mindstorms Set SpecIF:contains LEGO Mindstorms Vehicle
- LEGO Mindstorms Set SpecIF:contains Chassis
- LEGO Mindstorms Set SpecIF:contains Body
- LEGO Mindstorms Set SpecIF:contains Drive Left
- LEGO Mindstorms Set SpecIF:contains Support Front
- LEGO Mindstorms Set SpecIF:contains Support Rear
- LEGO Mindstorms Set SpecIF:contains Controller
- LEGO Mindstorms Set SpecIF:contains Track Sensor
- LEGO Mindstorms Set SpecIF:contains Collision Alarm Sensor
- LEGO Mindstorms Set SpecIF:contains Drive Right
- LEGO Mindstorms Vehicle dcterms:hasPart Chassis
- LEGO Mindstorms Vehicle dcterms:hasPart Body
- LEGO Mindstorms Vehicle dcterms:hasPart Drive Left
- LEGO Mindstorms Vehicle dcterms:hasPart Support Front
- LEGO Mindstorms Vehicle dcterms:hasPart Support Rear
- LEGO Mindstorms Vehicle dcterms:hasPart Controller
- LEGO Mindstorms Vehicle dcterms:hasPart Track Sensor
- LEGO Mindstorms Vehicle dcterms:hasPart Collision Alarm Sensor
- LEGO Mindstorms Vehicle dcterms:hasPart Drive Right
- Drive to Target dcterms:hasPart Navigate
- Drive to Target dcterms:hasPart Follow the Road
- Drive to Target dcterms:hasPart Brake in an Emergency
- Drive to Target dcterms:hasPart Turn Right
- Drive to Target dcterms:hasPart Turn Left
- Set Radius dcterms:hasPart Calculate Accelerations
- Set Speed dcterms:hasPart Calculate Accelerations
- Brake in an Emergency dcterms:hasPart Calculate Accelerations
- Calculate Accelerations dcterms:hasPart Set Acceleration Left
- Calculate Accelerations dcterms:hasPart Set Acceleration Right
- Calculate Accelerations dcterms:hasPart Apply Brake
- Turn Left dcterms:hasPart Select an adequate Speed
- Turn Left dcterms:hasPart Set Radius
- Turn Right dcterms:hasPart Set Radius
- Follow the Road dcterms:hasPart Set Radius
- Turn Right dcterms:hasPart Select an adequate Speed
- Follow the Road dcterms:hasPart Select an adequate Speed
- Select an adequate Speed dcterms:hasPart Set Speed
- Navigation IREB:refines Transport to Target
- Road Driving IREB:refines Transport to Target
- Safe Driving IREB:refines Transport to Target
- Obstacle Avoidance IREB:refines Transport to Target
- Loacation as GPS Coordinate IREB:refines Transport to Target
- Location as Postal Address IREB:refines Transport to Target
- Follow the Road oslc_rm:satisfies Road Driving
- Select an adequate Speed oslc_rm:satisfies Safe Driving
- Navigate oslc_rm:satisfies Navigation
- Set Acceleration Left sysml:Allocate Drive Left
- Apply Brake sysml:Allocate Drive Left
- Calculate Accelerations sysml:Allocate Controller
- Set Acceleration Right sysml:Allocate Drive Right
- Apply Brake sysml:Allocate Drive Right
- Original Requirement Specification SpecIF:shows Road Driving
- Original Requirement Specification SpecIF:shows Safe Driving
- Original Requirement Specification SpecIF:shows Navigation
- Original Requirement Specification SpecIF:shows Obstacle Avoidance
- Original Requirement Specification SpecIF:shows Transport to Target
- Original Requirement Specification SpecIF:shows Loacation as GPS Coordinate
- Original Requirement Specification SpecIF:shows Location as Postal Address
- Physical Decomposition SpecIF:shows Controller
- Physical Decomposition SpecIF:shows Support Front
- Physical Decomposition SpecIF:shows Drive Right
- Physical Decomposition SpecIF:shows Body
- Physical Decomposition SpecIF:shows Chassis
- Physical Decomposition SpecIF:shows Collision Alarm Sensor
- Physical Decomposition SpecIF:shows LEGO Mindstorms Set
- Physical Decomposition SpecIF:shows Support Rear
- Physical Decomposition SpecIF:shows Track Sensor
- Physical Decomposition SpecIF:shows LEGO Mindstorms Vehicle
- Physical Decomposition SpecIF:shows Drive Left
- Functional Decomposition SpecIF:shows Controller
- Functional Decomposition SpecIF:shows Follow the Road
- Functional Decomposition SpecIF:shows Set Acceleration Right
- Functional Decomposition SpecIF:shows Calculate Accelerations
- Functional Decomposition SpecIF:shows Turn Right
- Functional Decomposition SpecIF:shows Drive to Target
- Functional Decomposition SpecIF:shows Navigate
- Functional Decomposition SpecIF:shows Brake in an Emergency
- Functional Decomposition SpecIF:shows Safe Driving
- Functional Decomposition SpecIF:shows Navigation
- Functional Decomposition SpecIF:shows Turn Left
- Functional Decomposition SpecIF:shows Set Radius
- Functional Decomposition SpecIF:shows Set Acceleration Left
- Functional Decomposition SpecIF:shows Drive Right
- Functional Decomposition SpecIF:shows Road Driving
- Functional Decomposition SpecIF:shows Set Speed
- Functional Decomposition SpecIF:shows Select an adequate Speed
- Functional Decomposition SpecIF:shows Drive Left
- Functional Decomposition SpecIF:shows Apply Brake
